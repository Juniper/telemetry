/*
 * $Id$
 *
 * Copyright (c) 2020, Juniper Networks, Inc.
 * All rights reserved.
 */

module junos-resiliency-interface {
    yang-version "1";

    namespace "http://juniper.net/yang/resiliency";

    prefix "jri";

    // import some basic types
    import openconfig-types { prefix oc-types; }
    import ietf-yang-types { prefix "yang"; }

    // meta
    organization "Juniper Networks Inc.";

    description
        "This module provides common data definitions for
        JUNOS exceptions for Routing, Forwarding and
        OS";

        revision "2019-10-31" {
            description
            "Initial definition of Juniper Resiliency Interface model";
            reference "1.0.0";
        }

	// identity statements

	// Exception-type identities

	identity EXCEPTION_TYPE {
	    description
		"Base identity for exception type";
	}

	identity EXCEPTION_IPV4 {
	    base EXCEPTION_TYPE;
	    description
		"IPv4 Exception Type";
	}

	identity EXCEPTION_IPV6 {
            base EXCEPTION_TYPE;
	    description
		"IPv6 Exception Type";
	}

	identity EXCEPTION_MPLS_IPV4 {
            base EXCEPTION_TYPE;
	    description
		"MPLS IPv4 Exception Type";
	}

	identity EXCEPTION_L2 {
	    base EXCEPTION_TYPE;
	    description
		"L2 Exception Type";
	}

	identity EXCEPTION_RAW {
	    base EXCEPTION_TYPE;
	    description
		"RAW Exception Type";
	}

	identity EXCEPTION_SOCKET {
	    base EXCEPTION_TYPE;
	    description
		"Socket Exception Type";
	}

	identity EXCEPTION_DOWNLOAD_PATH {
	    base EXCEPTION_TYPE;
	    description
		"Download-path Exception Type";
	}

	identity EXCEPTION_OS_COUNTER {
	    base EXCEPTION_TYPE;
	    description
		"OS Counter Exception Type";
	}

	// Exception sub-type identities

	identity EXCEPTION_SUBTYPE {
	    description
		"Base subtype identity for exceptions";
	}

	identity FIREWALL {
	    base EXCEPTION_SUBTYPE;
	    description
		"Discard due to firewall exception";
	}

	identity L3 {
            base EXCEPTION_SUBTYPE;
	    description
		"Base identity for L3";
	}

	identity BRIDGING {
            base EXCEPTION_SUBTYPE;
	    description
		"Base identity for Bridging";
	}

	// Owner identities

	identity OWNER_TYPE {
            description
		"Base subtype identity for exception owner";
	}

	identity ROUTING {
            base OWNER_TYPE;
	    description
		"Exceptions generated by Routing Daemon";
	}

	identity FORWARDING {
            base OWNER_TYPE;
	    description
		"Exceptions generated by Forwarding";
	}

	identity KERNEL {
	    base OWNER_TYPE;
	    description
		"Exceptions generated by Kernel";
	}

	// protocol identities

	identity PROTOCOL_TYPE {
            description
            "Base identity for IP protocol numbers";
	}

	identity ICMP {
            base PROTOCOL_TYPE;
	    description
		"Internet Control Message Protocol";
	}

	identity TCP {
	    base PROTOCOL_TYPE;
	    description
		"Transmission Control Protocol";
	}

	identity UDP {
            base PROTOCOL_TYPE;
	    description
		"User Datagram Protocol";
	}

	identity RSVP {
            base PROTOCOL_TYPE;
	    description
		"Resource Reservation Protocol";
	}

	identity GRE {
            base PROTOCOL_TYPE;
	    description
		"Generic Routing Encapsulation";
	}

	identity OSPF {
            base PROTOCOL_TYPE;
	    description
		"Open Shortest Path First";
	}

	// grouping defination for routing

	identity STATUS_TYPE {
	    description
		"Base subtype identity for exception krt operation status";
	}

	identity SUCCESS {
	    base STATUS_TYPE;
	    description
		"Exceptions generated by status Success";
	}

	identity DEFER {
	    base STATUS_TYPE;
	    description
		"Exceptions generated by status Defer";
	}

	identity FULL {
	    base STATUS_TYPE;
	    description
		"Exceptions generated by operation Full";
	}

	identity BLOCKED {
	    base STATUS_TYPE;
	    description
		"Exceptions generated by status Blocked";
	}

	identity NOTFOUND {
	    base STATUS_TYPE;
	    description
		"Exceptions generated by status NotFound";
	}

	identity NH_NOSUPPT {
	    base STATUS_TYPE;
	    description
		"Exceptions generated by status NexthopNoSupport";
	}

	identity CANCELLED {
	    base STATUS_TYPE;
	    description
		"Exceptions generated by status Cancelled";
	}

	identity ASYNC {
	    base STATUS_TYPE;
	    description
		"Exceptions generated by status Async";
	}

	identity RETRY {
	    base STATUS_TYPE;
	    description
		"Exceptions generated by status Retry";
	}

	identity DONE {
	    base STATUS_TYPE;
	    description
		"Exceptions generated by status Done";
	}

	identity TAKEN_CARE {
	    base STATUS_TYPE;
	    description
		"Exceptions generated by status TakenCare";
	}

	identity DEFER_ADD {
	    base STATUS_TYPE;
	    description
		"Exceptions generated by status DeferAdd";
	}

	identity FAIL {
	    base STATUS_TYPE;
	    description
		"Exceptions generated by status Fail";
	}

	identity FORCE_DONE {
	    base STATUS_TYPE;
	    description
		"Exceptions generated by status ForceDone";
	}

	identity PARTIAL {
	    base STATUS_TYPE;
	    description
		"Exceptions generated by status Partial";
	}

	identity MEMFULL {
	    base STATUS_TYPE;
	    description
		"Exceptions generated by status MemFull";
	}

	identity HANDLED {
	    base STATUS_TYPE;
	    description
		"Exceptions generated by status Handled";
	}

	identity FREED {
	    base STATUS_TYPE;
	    description
		"Exceptions generated by status Freed";
	}

	identity FAILURE {
	    base STATUS_TYPE;
	    description
		"Exceptions generated by status Failure";
	}

	identity STATUS_UNAVAILABLE {
	    base STATUS_TYPE;
	    description
		"Exceptions
		generated
		by
		status
		Unavailable";
	}

	identity OP_TYPE {
	    description
		"Base subtype identity for exception krt operation type";
	}

	identity NOP {
	    base OP_TYPE;
	    description
		"Exceptions generated by Nooperation operation";
	}

	identity DELETE {
	    base OP_TYPE;
	    description
		"Exceptions generated by delete operation";
	}

	identity ADD {
	    base OP_TYPE;
	    description
		"Exceptions generated by add operation";
	}

	identity CHANGE {
	    base OP_TYPE;
	    description
		"Exceptions generated by change operation";
	}

	identity GET {
	    base OP_TYPE;
	    description
		"Exceptions generated by get operation";
	}

	identity OP_UNAVAILABLE {
	    base STATUS_TYPE;
	    description
		"Exceptions generated by operation Unavailable";
	}

	identity RNH_TYPE {
	    description
		"Base subtype identity for exception krt route nexthop type";
	}

	identity RT_NH_UNUSABLE {
	    base RNH_TYPE;
	    description
		"Exceptions generated by unusable route";
	}

	identity RT_NH_INTERFACE {
	    base RNH_TYPE;
	    description
		"Exceptions generated by direct interface route type";
	}

	identity RT_NH_TABLE {
	    base RNH_TYPE;
	    description
		"Exceptions generated by next routing table type";
	}

	identity RT_NH_INDIRECT {
	    base RNH_TYPE;
	    description
		"Exceptions generated by Indirect nexthop type";
	}

	identity RT_NH_ROUTER {
	    base RNH_TYPE;
	    description
		"Exceptions generated by nexthop is/are router(s)";
	}

	identity RT_NH_IPV4_MULTICAST {
	    base RNH_TYPE;
	    description
		"Exceptions generated by multicast next hop list route IPv4`";
	}

	identity RT_NH_IPV6_MULTICAST {
	    base RNH_TYPE;
	    description
		"Exceptions generated by multicast next hop list route IPv6";
	}

	identity RT_NH_IFLIST {
	    base RNH_TYPE;
	    description
		"Exceptions generated by route nexhop type Interface list";
	}

	identity RNH_LOCAL {
	    base RNH_TYPE;
	    description
		"Exceptions generated by route to the local address of an
		interface";
	}

	identity RT_NH_REJECT {
	    base RNH_TYPE;
	    description
		"Exceptions generated by reject route";
	}

	identity RT_NH_BLACKHOLE {
	    base RNH_TYPE;
	    description
		"Exceptions generated by black hole route";
	}

	identity RT_NH_RECEIVE {
	    base RNH_TYPE;
	    description
		"Exceptions generated by special router alert packets";
	}

	identity RT_NH_MRECEIVE {
	    base RNH_TYPE;
	    description
		"Exceptions generated by a local multicast receive route";
	}

	identity RT_NH_MRESOLVE {
	    base RNH_TYPE;
	    description
		"Exceptions generated by multicast resolve next-hop";
	}

	identity RT_NH_MDISCARD {
	    base RNH_TYPE;
	    description
		"Exceptions generated by multicast discard route";
	}

	identity RT_NH_TABLE_RECEIVE {
	    base RNH_TYPE;
	    description
		"Exceptions generated by special router alert packets - vrf
		bound";
	}

	identity RT_NH_SERVICE {
	    base RNH_TYPE;
	    description
		"Exceptions generated by service next hop";
	}

	identity RT_NH_FLOOD {
	    base RNH_TYPE;
	    description
		"Exceptions generated by flooding";
	}

	identity RT_NH_CFNH {
	    base RNH_TYPE;
	    description
		"Exceptions generated  by cfnh next hop";
	}

	identity RT_NH_CHAIN {
	    base RNH_TYPE;
	    description
		"Exceptions generated by chain next hop";
	}

	identity RT_NH_NSRHOLD {
	    base RNH_TYPE;
	    description
		"Exceptions generated  by standby mode routes cannot be
		resolved due to some conditions";
	}

	identity RT_NH_INDXD {
	    base RNH_TYPE;
	    description
		"Exceptions generated by route nexhop indexed";
	}

	identity RT_NH_FICTITIOUS {
	    base RNH_TYPE;
	    description
		"Exceptions generated by a fictitious next hop, for krt code";
	}

	identity RT_NH_TUNNEL {
	    base RNH_TYPE;
	    description
		"Exceptions generated  by Tunnel next hop";
	}

	identity RT_NH_IPV4_MCAST_COMP {
	    base RNH_TYPE;
	    description
		"Exceptions generated by Multicast composite next hop";
	}

	identity RT_NH_IPV6_MCAST_COMP {
	    base RNH_TYPE;
	    description
		"Exceptions generated by Multicast composite next hop";
	}

	identity RT_NH_IFLIST_MCAST_COMP {
	    base RNH_TYPE;
	    description
		"Exceptions generated by Interface list based on MCAST_COMP";
	}

	identity RT_NH_RPF_MCAST_COMP {
	    base RNH_TYPE;
	    description
		"Exceptions generated by Interface list based on MCAST_COMP";
	}

	identity RT_NH_MULTICAST_IFL {
	    base RNH_TYPE;
	    description
		"Exceptions generated  by OIF nexthop in multicast composite
		nh";
	}

	identity RT_NH_OCNH {
	    base RNH_TYPE;
	    description
		"Exceptions generated by For adding a radix root in
		rt_nexthops_root for OCNH";
	}

	identity RT_NH_LIST {
	    base RNH_TYPE;
	    description
		"Exceptions generated by Explicit unilist representation in
		rpd";
	}

	identity RT_NH_PFE_TABLE {
	    base RNH_TYPE;
	    description
		"Exceptions generated by next pfe and routing table";
	}

	identity RT_NH_PRIVATE_COMP {
	    base RNH_TYPE;
	    description
		"Exceptions generated by  composite next hop";
	}

	identity RT_NH_PRIVATE_UNICAST {
	    base RNH_TYPE;
	    description
		"Exceptions generated by internal unicast nexthop and user
		specific";
	}

	identity RT_NH_PRIVATE_INDXD {
	    base RNH_TYPE;
	    description
		"Exceptions generated by  internal indexed nexthop and user
		specific";
	}

	identity RT_NH_TUNNEL_COMP {
	    base RNH_TYPE;
	    description
		"Exceptions generated by Tunnel Composite next hop";
	}

	identity RT_NH_PRIVATE_OPAQUE {
	    base RNH_TYPE;
	    description
		"Exceptions generated by User specific opaque nexthop";
	}

	identity RT_NH_FRR_INDIRECT {
	    base RNH_TYPE;
	    description
		"Exceptions generated by FRR indirect nexthop used by resolver
		to preserve session IDees  when doing recursive resolution and
		INH compression";
        }

	identity RT_NH_END {
	    base RNH_TYPE;
	    description
		"Exceptions generated by rt end";
	}


	identity RNH_UNAVAILABLE {
	    base RNH_TYPE;
	    description
		"Exceptions generated by route nexthop not available";
	}



	// grouping definitions for descriptors

	grouping common-incident-descriptor {
	    container incident-descriptor {
		leaf exception-code {
		    type string;
		    description
			"Code to uniquely identify any exception";
		}
		leaf description {
		    type string;
		    description
			"Will include details about exception";
		}
		leaf host-id {
		    type string;
		    description
			"Hostname of the device generating this exception";
		}
		leaf resource-id {
		    type string;
		    description
			"Any other additional information to identify the control plane
			entity, can be input-interface, Output-interface, FPC slot etc.";
		}
		leaf timestamp {
		    type oc-types:timeticks64;
		    description
			"Timestamp when this exception happened";
		}
		leaf id {
		    type uint64;
		    description
			"Running counter for exceptions";
		}
	    }
	}

	grouping common-exception-descriptor {
	    leaf exception-type {
		type identityref {
		    base EXCEPTION_TYPE;
		}
		description
		    "Type or Category of exception";
	    }
	    leaf exception-owner {
		type identityref {
		    base OWNER_TYPE;
		}
		description
		    "Component to which this exception belongs to, can be ROUTING,
		    FORWARDING or KERNEL";
	    }
	}

	grouping common-ip-descriptor-state {
	    leaf destination-addr {
		type string;
		description
		    "IPV4 or IPV6 destination address from the header";
	    }
	    leaf source-addr {
		type string;
		description
		    "IPV4 or IPV6 source address from the header";
	    }
	    leaf destination-port {
		type uint16;
		description
		    "The destination port identifier in the TCP/UDP header";
	    }
	    leaf source-port {
		type uint16;
		description
		    "The source port identifier in the TCP/UDP header";
	    }
	    leaf protocol {
		type union {
		    type uint8;
		    type identityref {
			base PROTOCOL_TYPE;
		    }
		}
		description
		    "The value of the protocol number in IP packet header";
	    }
	    leaf tos {
		type uint8;
		description
		    "The value of a Differentiated Services Code Point (DSCP)";
	    }
	    leaf packet-len {
		type uint32;
		description
		    "The total length of the IPv4/IPV6 packet";
	    }
	    leaf interface-num {
		type uint32;
		description
		    "The index of IP interface";
	    }
	    leaf ip-fragment {
		type uint32;
		description
		    "The value of the Identification field in the IPv4 packet header
		    or in the IPv6 Fragment header";
	    }
	    leaf tcp-flags {
		type uint32;
		description
		    "TCP control bits";
	    }
	}

	grouping ipv4-descriptor-state {
	    container ipv4-descriptor {
		uses common-ip-descriptor-state;
		description
                    "The IPv4 descriptor State";
	    }
	}

	grouping ipv6-descriptor-state {
	    container ipv6-descriptor {
		uses common-ip-descriptor-state;
                description
                    "The IPv6 descriptor State";
	    }
	}

	grouping mpls-descriptor-state {
	    container mpls-ipv4-descriptor {
		uses common-ip-descriptor-state;
		leaf label {
		    type uint32;
		    description
			"MPLS label fetched from MPLS header";
		}
	    }
	}

	grouping l2-descriptor-state {
	    container l2-descriptor {
		leaf dest-mac-addr {
		    type yang:mac-address;
		    description
			"Destination MAC address";
		}
		leaf src-mac-addr {
		    type yang:mac-address;
		    description
			"Source MAC address";
		}
		leaf ether-type {
		    type string;
		    description
			"Ether type";
		}
	    }
	}

	grouping raw-descriptor-state {
	    container raw-descriptor {
		leaf generic-header {
		    type string;
		    description
			"Raw packet Byte Data";
		}
	    }
	}

	grouping forwarding-profile-top {
	    list forwarding-profile {
		key "id";
		description
		    "List of Data-path exceptions";

		leaf id {
		    type leafref {
			path "../incident-descriptor/id";
		    }
		    description
			"Running counter for exceptions";
		}
		uses common-exception-descriptor;
		leaf exception-subtype {
		    type identityref {
			base EXCEPTION_SUBTYPE;
		    }
		    description
			"Subcategory of the exception, can be L3, FIREWALL, BRIDGING etc.";
		}

		uses common-incident-descriptor;
		uses ipv4-descriptor-state;
		uses ipv6-descriptor-state;
		uses mpls-descriptor-state;
		uses l2-descriptor-state;
		uses raw-descriptor-state;
	    }
	}

	grouping download-path-descriptor-state {
	    container download-path-descriptor {
		leaf object-id {
		    type uint64;
		    description
			"Database identifiers of individual clients in system,
			can be CNH table, flood nh etc.";
		}
		leaf krt-status {
		    type identityref {
			base STATUS_TYPE;
		    }
		    description
			"krt status";
		}
		leaf errno {
		    type string;
		    description
			"Error code reported by Kernel";
		}
		leaf route-prefix {
		    type string;
		    description
			"Route for which this exception is reported";
		}
		leaf nexthop-index {
		    type uint32;
		    description
			"Nexthop index for which this exception is reported";
		}
		leaf krtq-op {
		    type identityref {
			base OP_TYPE;
		    }
		    description
			"Krtq operation for which this exception is reported";
		}
		leaf nexthop-handle {
		    type identityref {
			base RNH_TYPE;
		    }
		    description
			"Nexthop handle for which this exception is reported";
		}
		leaf sequence-number {
		    type uint32;
		    description
			"Sequence Number for which this exception is reported";
		}
	    }
	}

	grouping os-socket-descriptor-state {
	    container os-socket-descriptor {
		leaf local-addr {
		    type string;
		    description
			"Local address of the socket";
		}
		leaf foreign-addr {
		    type string;
		    description
			"Remote/Foreign address of the socket";
		}
		leaf local-port {
		    type uint16;
		    description
			"Local port of the socket";
		}
		leaf foreign-port {
		    type uint16;
		    description
			"Remote/Foreign port of the socket";
		}
	    }
	}

	grouping routing-profile-top {
	    list routing-profile {
		key "id";
		description
		    "List of Routing exceptions";

		leaf id {
		    type leafref {
			path "../incident-descriptor/id";
		    }
		    description
			"Running counter of Exceptions";
		}
		uses common-exception-descriptor;
		uses common-incident-descriptor;

		uses download-path-descriptor-state;
		uses os-socket-descriptor-state;
	    }
	}

	grouping os-counters-state {
	    container os-counters {
		leaf isrs-low-on-mbuf-clusters {
		    type yang:counter32;
		    description
			"NETISR low on mbuf clusters";
		}
                leaf isrs-mbuf-alloc-failures {
                    type yang:counter64;
                    description
                        "mbuf allocation failures";
                }
                leaf isrs-mbuf-cluster-alloc-failures {
                    type yang:counter64;
                    description
                        "mbuf cluster allocation failures";
                }
		leaf nw-queue-drops-ether {
		    type yang:counter32;
		    description
			"Ethernet input queue drops";
		}
		leaf nw-queue-drops-ip {
		    type yang:counter32;
		    description
			"IPv4 queue drops";
		}
		leaf nw-queue-drops-ipv6 {
		    type yang:counter32;
		    description
			"IPV6 queue drops";
		}
		leaf nw-queue-drops-arp {
		    type yang:counter32;
		    description
			"ARP queue drops";
		}
	    }
	}

	grouping os-profile-top {
	    container os-profile {
		uses common-exception-descriptor;
		uses common-incident-descriptor;
		uses os-socket-descriptor-state;
		uses os-counters-state;
	    }
	}

	grouping log-descriptor-state {
	    list log-descriptor {
		key "id";
		description
		    "List of meta-data fields in exception";

		leaf id {
		    type uint64;
		    description
			"Running number of meta-data fields in exception";
		}
		leaf log-entry-key {
		    type string;
		    description
			"Key of meta-data field in exception";
		}
		leaf log-entry-value {
		    type string;
		    description
			"Value of meta-data field in exception";
		}
	    }
	}

	grouping log-profile-top {
	    list log-profile {
		key "id";
		description
		    "List of generic exceptions";

		leaf id {
		    type leafref {
			path "../incident-descriptor/id";
		    }
		    description
			"Running counter of exceptions";
		}
		uses common-exception-descriptor;
		uses common-incident-descriptor;

		uses log-descriptor-state;
	    }
	}

	grouping exception-profiles-top {
	    container junos {
		config false;
		container exception-profiles {
		    uses forwarding-profile-top;
		    uses routing-profile-top;
		    uses os-profile-top;
		    uses log-profile-top;
                    description
                        "List of Exception profiles";
		}
	    }
	}

	uses exception-profiles-top;
}
