module junos-arp {

    yang-version "1";

    namespace "http://juniper.net/yang/arp";

    prefix "jnx-arp";

    organization "Juniper Networks";

    revision "2020-07-17" {
        description "Junos ARP Information data model";
        reference "1.0.0";
    }

    container "arp-information" {
        config false;

        description "This container hold all the ARP information.";
        container ipv4 {

            description "This container hold IPv4 information.";
            container neighbors {

                description "This container hold neighbors information.";
                list neighbor {
                    key "ip";
                    description "This container hold neighbor information.";
                    leaf ip {
                        type string;
                        description "IPv4 destination address.";
                    }

                    container state {
                        leaf ip {
                            type string;
                            description "IPv4 destination address.";
                        }

                        leaf link-layer-address {
                            type string;
                            description "The link-layer address of the neighbor node.";
                        }

                        leaf origin {
                            type enumeration{
                                enum STATIC {
                                    description "Origin is static.";
                                    }
                                enum DYNAMIC {
                                    description "Origin is dynamic.";
                                    }
                                enum  OTHER {
                                    description "Origin is neither staic nor dynamic.";
                                    }
                            }
                            description "The origin of this address.";
                        }

                        leaf host-name {
                            type string;
                            description "Host name for this neighbor entry";
                        }

                        leaf table-id {
                            type uint32;
                            description "Routing table ID for this neighbor entry";
                        }

                        leaf neighbor-state {
                            type enumeration {
                                enum INCOMPLETE {
                                    description
                                    "Address resolution is in progress, and the link-layer
                                    address of the neighbor has not yet been
                                    determined.";
                                 }

                                enum REACHABLE {
                                    description
                                    "Roughly speaking, the neighbor is known to have been
                                    reachable recently (within tens of seconds ago).";
                                }

                                enum PROBE {
                                    description
                                    "The neighbor is no longer known to be reachable, and
                                    unicast Neighbor Solicitation probes are being sent
                                    to verify reachability.";
                                }

                                enum PERM {
                                    description
                                    "The neighbor is statically configured";
                                }
                            }
                            description "ARP neighbor FSM state";
                         }

                        leaf expiry {
                            type uint32;
                            description "lifetime of ARP neighbor entry";
                        }

                        leaf is-publish {
                            type boolean;
                            description "whether the ARP neighbor is a published one";
                        }

                        leaf interface-name {
                            type string;
                            description "interface on which this neighbor entry was learnt";
                        }

                        leaf logical-router-id {
                            type uint8;
                            description "logical router ID for this neighbor entry";
                        }
                    }
                }
            }
        }
    }
}
