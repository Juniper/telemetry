module jnx-openconfig-dev {
  yang-version "1";

  namespace "http://yang.juniper.net/openconfig/deviations"; 

  prefix "oc-dev";

  import openconfig-interfaces { prefix oc-if; }
  import openconfig-if-ethernet { prefix oc-eth; }
  import openconfig-if-ip { prefix oc-ip; }
  import openconfig-if-ip-ext { prefix oc-ip-ext; }

  import openconfig-bgp { prefix oc-bgp; }
  import openconfig-bgp-policy { prefix oc-bgp-pol; }

  import openconfig-routing-policy { prefix oc-rpol; }

  import openconfig-mpls { prefix oc-mpls; }

  import ietf-inet-types { prefix inet; }
  import openconfig-local-routing { prefix oc-loc-rt; }

  import openconfig-lldp { prefix oc-lldp; }

  import openconfig-vlan { prefix oc-vlan; }

  import openconfig-vlan-types { prefix oc-vlan-types; }

  import openconfig-network-instance { prefix oc-ni; }


  organization "Juniper Networks";

  description
    "This module contains OpenConfig deviations for all modules";

  revision "2018-10-30" {
    description "Add deviation for specific to preference (MPLS TE)";
    reference "JUNOS 18.2X75-D30, 18.4 and above";
  }

  revision "2018-08-08" {
    description "Add deviations specific to associated-rsvp-session (MPLS TE)";
  }

  revision "2018-02-05" {
    description "add support for BGP Version 4.0.1";
    reference "TBD";
  }
  revision "2015-05-19" {
    description "Initial revision";
    reference "TBD";
  }

  deviation /oc-if:interfaces/oc-if:interface/oc-if:subinterfaces/oc-if:subinterface/oc-if:index {
       deviate replace {
           type uint32;
       }
  }

  deviation "/oc-if:interfaces/oc-if:interface/oc-if:subinterfaces/oc-if:subinterface/oc-ip:ipv4/oc-ip:neighbors/" + 
            "oc-ip:neighbor/oc-ip:config" {
    description
      "Junos does not support interface neighbor config";
    deviate not-supported;
  }

  deviation "/oc-if:interfaces/oc-if:interface/oc-if:subinterfaces/oc-if:subinterface/oc-ip:ipv6/oc-ip:neighbors/" + 
            "oc-ip:neighbor/oc-ip:config" {
    description
          "Junos does not support interface neighbor config";
    deviate not-supported;
  }

  deviation "/oc-if:interfaces/oc-if:interface/oc-if:subinterfaces/oc-if:subinterface/oc-ip:ipv6/oc-ip:neighbors/" +
            "oc-ip:neighbor/oc-ip:state/oc-ip:is-router" {
    deviate replace {
        type boolean;
    }
    description "[adapted from IETF IP model RFC 7277]
                 Indicates that the neighbor node acts as a router.
                 Junos supports is-router as type boolean";
  }

  deviation /oc-if:interfaces/oc-if:interface/oc-if:subinterfaces/oc-if:subinterface/oc-ip:ipv6/oc-ip-ext:autoconf {
    description
          "Junos does not support ipv6 autoconf";
    deviate not-supported;
  }
  deviation /oc-if:interfaces/oc-if:interface/oc-if:subinterfaces/oc-if:subinterface/oc-ip:ipv6/oc-ip:state/oc-ip:dup-addr-detect-transmits {
      description
          "Junos does not support address ipv6 duplicate address transmits at interface level";
      deviate not-supported;
  }

  // deviate for opeconfig-interfaces.yang
  deviation /oc-if:interfaces/oc-if:interface/oc-if:state/oc-if:counters/oc-if:in-discards {
      description
          "Junos does not support in-discards at interface level";
      deviate not-supported;
  }
  deviation /oc-if:interfaces/oc-if:interface/oc-if:state/oc-if:counters/oc-if:in-unknown-protos {
      description
          "Junos does not support last-clear at interface level";
      deviate not-supported;
  }
  deviation /oc-if:interfaces/oc-if:interface/oc-if:state/oc-if:counters/oc-if:last-clear {
      description
          "Junos does not support last-clear at interface level";
      deviate not-supported;
  }

  deviation /oc-if:interfaces/oc-if:interface/oc-if:subinterfaces/oc-if:subinterface/oc-if:state/oc-if:counters/oc-if:in-broadcast-pkts {
      description
          "Junos does not support in-broadcast-pkts at subinterface level";
      deviate not-supported;
  }
  deviation /oc-if:interfaces/oc-if:interface/oc-if:subinterfaces/oc-if:subinterface/oc-if:state/oc-if:counters/oc-if:in-discards {
      description
          "Junos does not support in-discrads at subinterface level";
      deviate not-supported;
  }
  deviation /oc-if:interfaces/oc-if:interface/oc-if:subinterfaces/oc-if:subinterface/oc-if:state/oc-if:counters/oc-if:in-errors {
      description
          "Junos does not support in-errors at subinterface level";
      deviate not-supported;
  }
  deviation /oc-if:interfaces/oc-if:interface/oc-if:subinterfaces/oc-if:subinterface/oc-if:state/oc-if:counters/oc-if:in-unknown-protos {
      description
          "Junos does not support in-unknown-protos at subinterface level";
      deviate not-supported;
  }
  deviation /oc-if:interfaces/oc-if:interface/oc-if:subinterfaces/oc-if:subinterface/oc-if:state/oc-if:counters/oc-if:out-broadcast-pkts {
      description
          "Junos does not support out-broadcast-pkts at subinterface level";
      deviate not-supported;
  }
  deviation /oc-if:interfaces/oc-if:interface/oc-if:subinterfaces/oc-if:subinterface/oc-if:state/oc-if:counters/oc-if:out-discards {
      description
          "Junos does not support out-discrads at subinterface level";
      deviate not-supported;
  }
  deviation /oc-if:interfaces/oc-if:interface/oc-if:subinterfaces/oc-if:subinterface/oc-if:state/oc-if:counters/oc-if:out-errors {
      description
          "Junos does not support out-errors at subinterface level";
      deviate not-supported;
  }
  deviation /oc-if:interfaces/oc-if:interface/oc-if:subinterfaces/oc-if:subinterface/oc-if:state/oc-if:counters/oc-if:last-clear {
      description
          "Junos does not support last-clear at subinterface level";
      deviate not-supported;
  }

  // deviate for opeconfig-if-ethernet.yang
  deviation /oc-if:interfaces/oc-if:interface/oc-eth:ethernet/oc-eth:state/oc-eth:effective-speed {
      description
          "Junos does not support effective speed at ethernet interface level";
      deviate not-supported;
  }
  deviation /oc-if:interfaces/oc-if:interface/oc-eth:ethernet/oc-eth:state/oc-eth:counters/oc-eth:in-mac-control-frames {
      description
          "Junos does not support in-mac-control-frame at ethernet interface level";
      deviate not-supported;
  }
  deviation /oc-if:interfaces/oc-if:interface/oc-eth:ethernet/oc-eth:state/oc-eth:counters/oc-eth:in-fragment-frames {
      description
          "Junos does not support in-fragment-frames at ethernet interface level";
      deviate not-supported;
  }
  deviation /oc-if:interfaces/oc-if:interface/oc-eth:ethernet/oc-eth:state/oc-eth:counters/oc-eth:in-8021q-frames {
      description
          "Junos does not support in-8021q-frames at ethernet interface level";
      deviate not-supported;
  }
  deviation /oc-if:interfaces/oc-if:interface/oc-eth:ethernet/oc-eth:state/oc-eth:counters/oc-eth:out-mac-control-frames {
      description
          "Junos does not support out-mac-control-frames at ethernet interface level";
      deviate not-supported;
  }
  deviation /oc-if:interfaces/oc-if:interface/oc-eth:ethernet/oc-eth:state/oc-eth:counters/oc-eth:out-8021q-frames {
      description
          "Junos does not support out-8021q-frames at ethernet interface level";
      deviate not-supported;
  }

  // Policy Deviations

  deviation /oc-rpol:routing-policy/oc-rpol:defined-sets/oc-bgp-pol:bgp-defined-sets/oc-bgp-pol:as-path-sets {
      deviate not-supported;
  }
  deviation /oc-rpol:routing-policy/oc-rpol:policy-definitions/oc-rpol:policy-definition/oc-rpol:statements/oc-rpol:statement/oc-rpol:conditions/oc-rpol:match-neighbor-set/oc-rpol:config/oc-rpol:match-set-options {
      deviate not-supported;
  }
  deviation /oc-rpol:routing-policy/oc-rpol:policy-definitions/oc-rpol:policy-definition/oc-rpol:statements/oc-rpol:statement/oc-rpol:conditions/oc-rpol:match-tag-set/oc-rpol:config/oc-rpol:match-set-options {
      deviate not-supported;
  }
  deviation /oc-rpol:routing-policy/oc-rpol:policy-definitions/oc-rpol:policy-definition/oc-rpol:statements/oc-rpol:statement/oc-rpol:conditions/oc-rpol:match-prefix-set/oc-rpol:config/oc-rpol:match-set-options {
      deviate not-supported;
  }
  deviation /oc-rpol:routing-policy/oc-rpol:policy-definitions/oc-rpol:policy-definition/oc-rpol:statements/oc-rpol:statement/oc-rpol:conditions/oc-bgp-pol:bgp-conditions/oc-bgp-pol:match-community-set/oc-bgp-pol:config/oc-bgp-pol:match-set-options {
      deviate not-supported;
  }
  deviation /oc-rpol:routing-policy/oc-rpol:policy-definitions/oc-rpol:policy-definition/oc-rpol:statements/oc-rpol:statement/oc-rpol:conditions/oc-bgp-pol:bgp-conditions/oc-bgp-pol:match-ext-community-set/oc-bgp-pol:config/oc-bgp-pol:match-set-options {
      deviate not-supported;
  }
  deviation /oc-rpol:routing-policy/oc-rpol:policy-definitions/oc-rpol:policy-definition/oc-rpol:statements/oc-rpol:statement/oc-rpol:conditions/oc-rpol:igp-conditions {
      deviate not-supported;
  }
  deviation /oc-rpol:routing-policy/oc-rpol:policy-definitions/oc-rpol:policy-definition/oc-rpol:statements/oc-rpol:statement/oc-rpol:conditions/oc-bgp-pol:bgp-conditions/oc-bgp-pol:as-path-length {
      deviate not-supported;
  }
  deviation /oc-rpol:routing-policy/oc-rpol:policy-definitions/oc-rpol:policy-definition/oc-rpol:statements/oc-rpol:statement/oc-rpol:conditions/oc-bgp-pol:bgp-conditions/oc-bgp-pol:match-as-path-set {
      deviate not-supported;
  }
  deviation /oc-rpol:routing-policy/oc-rpol:policy-definitions/oc-rpol:policy-definition/oc-rpol:statements/oc-rpol:statement/oc-rpol:conditions/oc-bgp-pol:bgp-conditions/oc-bgp-pol:config/oc-bgp-pol:next-hop-in {
      deviate replace {
        type inet:ip-address-no-zone;
      }
  }
  deviation /oc-rpol:routing-policy/oc-rpol:policy-definitions/oc-rpol:policy-definition/oc-rpol:statements/oc-rpol:statement/oc-rpol:conditions/oc-bgp-pol:bgp-conditions/oc-bgp-pol:config/oc-bgp-pol:afi-safi-in {
      deviate add {
          max-elements 1;
      }
  }
  deviation /oc-rpol:routing-policy/oc-rpol:policy-definitions/oc-rpol:policy-definition/oc-rpol:statements/oc-rpol:statement/oc-rpol:actions/oc-bgp-pol:bgp-actions/oc-bgp-pol:config/oc-bgp-pol:set-next-hop {
      deviate replace {
        type inet:ip-address-no-zone;
      }
  }
  deviation /oc-rpol:routing-policy/oc-rpol:policy-definitions/oc-rpol:policy-definition/oc-rpol:statements/oc-rpol:statement/oc-rpol:actions/oc-bgp-pol:bgp-actions/oc-bgp-pol:set-as-path-prepend/oc-bgp-pol:config/oc-bgp-pol:repeat-n {
      deviate not-supported;
  }
  deviation /oc-rpol:routing-policy/oc-rpol:policy-definitions/oc-rpol:policy-definition/oc-rpol:statements/oc-rpol:statement/oc-rpol:actions/oc-bgp-pol:bgp-actions/oc-bgp-pol:config/oc-bgp-pol:set-med {
      deviate replace {
         type uint32;
      }
  }
  deviation /oc-rpol:routing-policy/oc-rpol:policy-definitions/oc-rpol:policy-definition/oc-rpol:statements/oc-rpol:statement/oc-rpol:actions/oc-bgp-pol:bgp-actions/oc-bgp-pol:set-community/oc-bgp-pol:inline {
      deviate not-supported;
  }
  deviation /oc-rpol:routing-policy/oc-rpol:policy-definitions/oc-rpol:policy-definition/oc-rpol:statements/oc-rpol:statement/oc-rpol:actions/oc-bgp-pol:bgp-actions/oc-bgp-pol:set-community/oc-bgp-pol:config/oc-bgp-pol:method {
      deviate not-supported;
  }
  deviation /oc-rpol:routing-policy/oc-rpol:policy-definitions/oc-rpol:policy-definition/oc-rpol:statements/oc-rpol:statement/oc-rpol:actions/oc-bgp-pol:bgp-actions/oc-bgp-pol:set-ext-community/oc-bgp-pol:inline {
      deviate not-supported;
  }
  deviation /oc-rpol:routing-policy/oc-rpol:policy-definitions/oc-rpol:policy-definition/oc-rpol:statements/oc-rpol:statement/oc-rpol:actions/oc-bgp-pol:bgp-actions/oc-bgp-pol:set-ext-community/oc-bgp-pol:config/oc-bgp-pol:method {
      deviate not-supported;
  }
  deviation /oc-rpol:routing-policy/oc-rpol:defined-sets/oc-rpol:prefix-sets/oc-rpol:prefix-set/oc-rpol:prefixes/oc-rpol:prefix/oc-rpol:config/oc-rpol:masklength-range {
    deviate replace {
      type string {
        pattern '([0-9]+\.\.[0-9]+)|exact';
      }
    }
  }

  
  // MPLS Deviations
  
  // Global
  deviation /oc-mpls:mpls/oc-mpls:global/oc-mpls:interface-attributes/oc-mpls:interface/oc-mpls:interface-ref {
      deviate not-supported;
  }
  // Signaling-Protocols
  deviation /oc-mpls:mpls/oc-mpls:signaling-protocols/oc-mpls:ldp {
      deviate not-supported;
  }
  deviation /oc-mpls:mpls/oc-mpls:signaling-protocols/oc-mpls:segment-routing {
      deviate not-supported;
  }
  deviation /oc-mpls:mpls/oc-mpls:signaling-protocols/oc-mpls:rsvp-te/oc-mpls:global/oc-mpls:hellos/oc-mpls:config/oc-mpls:hello-interval {
      deviate replace {
          type uint16 {
              range 1..60;
          }
          units seconds;
          default 9;
      }
  }
  deviation /oc-mpls:mpls/oc-mpls:signaling-protocols/oc-mpls:rsvp-te/oc-mpls:global/oc-mpls:soft-preemption/oc-mpls:config/oc-mpls:soft-preemption-timeout {
      deviate replace {
          type uint16 {
              range 1..180;
          }
          default 30;
      }
  }
  deviation /oc-mpls:mpls/oc-mpls:signaling-protocols/oc-mpls:rsvp-te/oc-mpls:global/oc-mpls:graceful-restart/oc-mpls:config/oc-mpls:restart-time {
      deviate replace {
          type uint32 {
              range 1..1800;
          }
      }
  }
  deviation /oc-mpls:mpls/oc-mpls:signaling-protocols/oc-mpls:rsvp-te/oc-mpls:global/oc-mpls:graceful-restart/oc-mpls:config/oc-mpls:recovery-time {
      deviate replace {
          type uint32 {
              range 1..3600;
          }
      }
  }
  deviation /oc-mpls:mpls/oc-mpls:signaling-protocols/oc-mpls:rsvp-te/oc-mpls:interface-attributes/oc-mpls:interface/oc-mpls:hellos/oc-mpls:config/oc-mpls:hello-interval {
      deviate replace {
          type uint16 {
              range 1..60;
          }
          units seconds;
          default 9;
      }
  }
  deviation /oc-mpls:mpls/oc-mpls:signaling-protocols/oc-mpls:rsvp-te/oc-mpls:interface-attributes/oc-mpls:interface/oc-mpls:authentication/oc-mpls:config/oc-mpls:authentication-key {
      deviate replace {
          type string {
              length 1..16;
          }
      }
  }
  deviation /oc-mpls:mpls/oc-mpls:signaling-protocols/oc-mpls:rsvp-te/oc-mpls:interface-attributes/oc-mpls:interface/oc-mpls:interface-ref {
      deviate not-supported;
  }
  // TE Global Attributes
  deviation /oc-mpls:mpls/oc-mpls:te-global-attributes/oc-mpls:srlgs/oc-mpls:srlg/oc-mpls:config/oc-mpls:cost {
      deviate replace {
          type uint32 {
              range 1..65535;
          }
      }
  }
  deviation /oc-mpls:mpls/oc-mpls:te-global-attributes/oc-mpls:srlgs/oc-mpls:srlg/oc-mpls:config/oc-mpls:value {
      deviate replace {
          type uint32 {
              range 1..max;
          }
      }
  }
  deviation /oc-mpls:mpls/oc-mpls:te-global-attributes/oc-mpls:srlgs/oc-mpls:srlg/oc-mpls:config/oc-mpls:name {
      deviate replace {
          type string {
              length 1..64;
          }
      }
  }
  deviation /oc-mpls:mpls/oc-mpls:te-global-attributes/oc-mpls:te-lsp-timers/oc-mpls:config/oc-mpls:install-delay {
      deviate replace {
          type uint16 {
              range 1..900;
          }
      }
  }
  // TE Interface Attributes
  deviation /oc-mpls:mpls/oc-mpls:te-interface-attributes/oc-mpls:interface/oc-mpls:config/oc-mpls:te-metric {
      deviate not-supported;
  }
  deviation /oc-mpls:mpls/oc-mpls:te-interface-attributes/oc-mpls:interface/oc-mpls:igp-flooding-bandwidth/oc-mpls:config/oc-mpls:threshold-specification {
      deviate not-supported;
  }
  deviation /oc-mpls:mpls/oc-mpls:te-interface-attributes/oc-mpls:interface/oc-mpls:igp-flooding-bandwidth/oc-mpls:config/oc-mpls:delta-percentage {
      deviate replace {
        type uint8 {
            range 1..20;
        }
      }
  }
  deviation /oc-mpls:mpls/oc-mpls:te-interface-attributes/oc-mpls:interface/oc-mpls:igp-flooding-bandwidth/oc-mpls:config/oc-mpls:up-thresholds {
      deviate not-supported;
  }
  deviation /oc-mpls:mpls/oc-mpls:te-interface-attributes/oc-mpls:interface/oc-mpls:igp-flooding-bandwidth/oc-mpls:config/oc-mpls:down-thresholds {
      deviate not-supported;
  }
  deviation /oc-mpls:mpls/oc-mpls:te-interface-attributes/oc-mpls:interface/oc-mpls:igp-flooding-bandwidth/oc-mpls:config/oc-mpls:up-down-thresholds {
      deviate not-supported;
  }
  deviation /oc-mpls:mpls/oc-mpls:te-interface-attributes/oc-mpls:interface/oc-mpls:interface-ref {
      deviate not-supported;
  }
  // LSPs
  deviation /oc-mpls:mpls/oc-mpls:lsps/oc-mpls:static-lsps {
      deviate not-supported;
  }
  deviation /oc-mpls:mpls/oc-mpls:lsps/oc-mpls:unconstrained-path {
      deviate not-supported;
  }
  deviation /oc-mpls:mpls/oc-mpls:lsps/oc-mpls:constrained-path/oc-mpls:named-explicit-paths/oc-mpls:named-explicit-path/oc-mpls:config/oc-mpls:name {
      deviate replace {
          type string {
              length 1..64;
          }
      }
  }
  deviation /oc-mpls:mpls/oc-mpls:lsps/oc-mpls:constrained-path/oc-mpls:tunnels/oc-mpls:tunnel/oc-mpls:config/oc-mpls:name {
      deviate replace {
          type string {
              length 1..64;
          }
      }
  }
  deviation /oc-mpls:mpls/oc-mpls:lsps/oc-mpls:constrained-path/oc-mpls:tunnels/oc-mpls:tunnel/oc-mpls:config/oc-mpls:type {
      deviate not-supported;
  }
  deviation /oc-mpls:mpls/oc-mpls:lsps/oc-mpls:constrained-path/oc-mpls:tunnels/oc-mpls:tunnel/oc-mpls:config/oc-mpls:signaling-protocol {
      deviate not-supported;
  }
  deviation /oc-mpls:mpls/oc-mpls:lsps/oc-mpls:constrained-path/oc-mpls:tunnels/oc-mpls:tunnel/oc-mpls:config/oc-mpls:metric-type {
      deviate not-supported;
  }
  deviation /oc-mpls:mpls/oc-mpls:lsps/oc-mpls:constrained-path/oc-mpls:tunnels/oc-mpls:tunnel/oc-mpls:config/oc-mpls:metric {
      deviate replace {
          type int32 {
              range 1..16777215;
          }
      }
  }
  deviation /oc-mpls:mpls/oc-mpls:lsps/oc-mpls:constrained-path/oc-mpls:tunnels/oc-mpls:tunnel/oc-mpls:config/oc-mpls:shortcut-eligible {
      deviate not-supported;
  }
  deviation /oc-mpls:mpls/oc-mpls:lsps/oc-mpls:constrained-path/oc-mpls:tunnels/oc-mpls:tunnel/oc-mpls:bandwidth/oc-mpls:config/oc-mpls:set-bandwidth {
      deviate replace {
          type uint64;
      }
      deviate add {
          units bps;
      }
  }
  deviation /oc-mpls:mpls/oc-mpls:lsps/oc-mpls:constrained-path/oc-mpls:tunnels/oc-mpls:tunnel/oc-mpls:bandwidth/oc-mpls:auto-bandwidth/oc-mpls:config/oc-mpls:min-bw {
      deviate replace {
          type uint64;
      }
      deviate add {
          units bps;
      }
  }
  deviation /oc-mpls:mpls/oc-mpls:lsps/oc-mpls:constrained-path/oc-mpls:tunnels/oc-mpls:tunnel/oc-mpls:bandwidth/oc-mpls:auto-bandwidth/oc-mpls:state/oc-mpls:min-bw {
      deviate replace {
          type uint64;
      }
      deviate add {
          units bps;
      }
  }
  deviation /oc-mpls:mpls/oc-mpls:lsps/oc-mpls:constrained-path/oc-mpls:tunnels/oc-mpls:tunnel/oc-mpls:bandwidth/oc-mpls:auto-bandwidth/oc-mpls:config/oc-mpls:adjust-interval {
      deviate replace {
          type uint32 {
              range 300..315360000;
          }
      }
      deviate add {
          units seconds;
      }
  }
  deviation /oc-mpls:mpls/oc-mpls:lsps/oc-mpls:constrained-path/oc-mpls:tunnels/oc-mpls:tunnel/oc-mpls:bandwidth/oc-mpls:auto-bandwidth/oc-mpls:config/oc-mpls:adjust-threshold {
      deviate replace {
        type uint8 {
            range 0..50;
        }
      }
  }
  deviation /oc-mpls:mpls/oc-mpls:lsps/oc-mpls:constrained-path/oc-mpls:tunnels/oc-mpls:tunnel/oc-mpls:bandwidth/oc-mpls:auto-bandwidth/oc-mpls:config/oc-mpls:max-bw {
      deviate replace {
          type uint64;
      }
      deviate add {
          units bps;
      }
  }
  deviation /oc-mpls:mpls/oc-mpls:lsps/oc-mpls:constrained-path/oc-mpls:tunnels/oc-mpls:tunnel/oc-mpls:bandwidth/oc-mpls:auto-bandwidth/oc-mpls:state/oc-mpls:max-bw {
      deviate replace {
          type uint64;
      }
      deviate add {
          units bps;
      }
  }
  deviation /oc-mpls:mpls/oc-mpls:lsps/oc-mpls:constrained-path/oc-mpls:tunnels/oc-mpls:tunnel/oc-mpls:bandwidth/oc-mpls:auto-bandwidth/oc-mpls:overflow/oc-mpls:config/oc-mpls:overflow-threshold {
      deviate not-supported;
  }
  deviation /oc-mpls:mpls/oc-mpls:lsps/oc-mpls:constrained-path/oc-mpls:tunnels/oc-mpls:tunnel/oc-mpls:bandwidth/oc-mpls:auto-bandwidth/oc-mpls:underflow/oc-mpls:config/oc-mpls:underflow-threshold {
      deviate not-supported;
  }
  deviation /oc-mpls:mpls/oc-mpls:lsps/oc-mpls:constrained-path/oc-mpls:tunnels/oc-mpls:tunnel/oc-mpls:p2p-tunnel-attributes/oc-mpls:p2p-primary-path/oc-mpls:p2p-primary-path {
      deviate add {
          max-elements 1;
      }
  }
  deviation /oc-mpls:mpls/oc-mpls:lsps/oc-mpls:constrained-path/oc-mpls:tunnels/oc-mpls:tunnel/oc-mpls:p2p-tunnel-attributes/oc-mpls:p2p-primary-path/oc-mpls:p2p-primary-path/oc-mpls:config/oc-mpls:cspf-tiebreaker {
      deviate not-supported;
  }
  deviation /oc-mpls:mpls/oc-mpls:lsps/oc-mpls:constrained-path/oc-mpls:tunnels/oc-mpls:tunnel/oc-mpls:p2p-tunnel-attributes/oc-mpls:p2p-primary-path/oc-mpls:p2p-primary-path/oc-mpls:config/oc-mpls:path-computation-method {
      deviate not-supported;
  }
  deviation /oc-mpls:mpls/oc-mpls:lsps/oc-mpls:constrained-path/oc-mpls:tunnels/oc-mpls:tunnel/oc-mpls:p2p-tunnel-attributes/oc-mpls:p2p-primary-path/oc-mpls:p2p-primary-path/oc-mpls:config/oc-mpls:path-computation-server {
      deviate not-supported;
  }
  deviation /oc-mpls:mpls/oc-mpls:lsps/oc-mpls:constrained-path/oc-mpls:tunnels/oc-mpls:tunnel/oc-mpls:p2p-tunnel-attributes/oc-mpls:p2p-primary-path/oc-mpls:p2p-primary-path/oc-mpls:config/oc-mpls:explicit-path-name {
      deviate not-supported;
  }
  deviation /oc-mpls:mpls/oc-mpls:lsps/oc-mpls:constrained-path/oc-mpls:tunnels/oc-mpls:tunnel/oc-mpls:p2p-tunnel-attributes/oc-mpls:p2p-primary-path/oc-mpls:p2p-primary-path/oc-mpls:config/oc-mpls:retry-timer {
      deviate not-supported;
  }
  deviation /oc-mpls:mpls/oc-mpls:lsps/oc-mpls:constrained-path/oc-mpls:tunnels/oc-mpls:tunnel/oc-mpls:p2p-tunnel-attributes/oc-mpls:p2p-primary-path/oc-mpls:p2p-primary-path/oc-mpls:candidate-secondary-paths {
      deviate not-supported;
  }
  deviation /oc-mpls:mpls/oc-mpls:lsps/oc-mpls:constrained-path/oc-mpls:tunnels/oc-mpls:tunnel/oc-mpls:p2p-tunnel-attributes/oc-mpls:p2p-secondary-paths/oc-mpls:p2p-secondary-path/oc-mpls:config/oc-mpls:cspf-tiebreaker {
      deviate not-supported;
  }
  deviation /oc-mpls:mpls/oc-mpls:lsps/oc-mpls:constrained-path/oc-mpls:tunnels/oc-mpls:tunnel/oc-mpls:p2p-tunnel-attributes/oc-mpls:p2p-secondary-paths/oc-mpls:p2p-secondary-path/oc-mpls:config/oc-mpls:path-computation-method {
      deviate not-supported;
  }
  deviation /oc-mpls:mpls/oc-mpls:lsps/oc-mpls:constrained-path/oc-mpls:tunnels/oc-mpls:tunnel/oc-mpls:p2p-tunnel-attributes/oc-mpls:p2p-secondary-paths/oc-mpls:p2p-secondary-path/oc-mpls:config/oc-mpls:path-computation-server {
      deviate not-supported;
  }
  deviation /oc-mpls:mpls/oc-mpls:lsps/oc-mpls:constrained-path/oc-mpls:tunnels/oc-mpls:tunnel/oc-mpls:p2p-tunnel-attributes/oc-mpls:p2p-secondary-paths/oc-mpls:p2p-secondary-path/oc-mpls:config/oc-mpls:explicit-path-name {
      deviate not-supported;
  }
  deviation /oc-mpls:mpls/oc-mpls:lsps/oc-mpls:constrained-path/oc-mpls:tunnels/oc-mpls:tunnel/oc-mpls:p2p-tunnel-attributes/oc-mpls:p2p-secondary-paths/oc-mpls:p2p-secondary-path/oc-mpls:config/oc-mpls:retry-timer {
      deviate not-supported;
  }

  // Local-Routing
  deviation /oc-loc-rt:local-routes/oc-loc-rt:static-routes/oc-loc-rt:static/oc-loc-rt:state/oc-loc-rt:prefix {
      deviate replace {
          type inet:ip-address;
      }
  }
  deviation /oc-loc-rt:local-routes/oc-loc-rt:static-routes/oc-loc-rt:static/oc-loc-rt:next-hops/oc-loc-rt:next-hop/oc-loc-rt:interface-ref {
      deviate not-supported;
  }
  deviation /oc-loc-rt:local-routes/oc-loc-rt:static-routes/oc-loc-rt:static/oc-loc-rt:next-hops/oc-loc-rt:next-hop/oc-loc-rt:config/oc-loc-rt:recurse {
      deviate not-supported;
  }
  deviation /oc-loc-rt:local-routes/oc-loc-rt:static-routes/oc-loc-rt:static/oc-loc-rt:next-hops/oc-loc-rt:next-hop/oc-loc-rt:state/oc-loc-rt:recurse {
      deviate not-supported;
  }
  deviation /oc-loc-rt:local-routes/oc-loc-rt:static-routes/oc-loc-rt:static/oc-loc-rt:next-hops/oc-loc-rt:next-hop/oc-loc-rt:config/oc-loc-rt:metric {
      deviate not-supported;
  }
  deviation /oc-loc-rt:local-routes/oc-loc-rt:local-aggregates/oc-loc-rt:aggregate/oc-loc-rt:state/oc-loc-rt:prefix {
      deviate replace {
          type inet:ip-address;
      }
  }
  
  // openconfig-lldp

  deviation /oc-lldp:lldp/oc-lldp:config/oc-lldp:suppress-tlv-advertisement {
      deviate not-supported;
  }
  deviation /oc-lldp:lldp/oc-lldp:state/oc-lldp:suppress-tlv-advertisement {
      deviate not-supported;
  }
  deviation /oc-lldp:lldp/oc-lldp:config/oc-lldp:system-name {
      deviate not-supported;
  }
  deviation /oc-lldp:lldp/oc-lldp:config/oc-lldp:system-description {
      deviate not-supported;
  }
  deviation /oc-lldp:lldp/oc-lldp:config/oc-lldp:chassis-id {
      deviate not-supported;
  }
  deviation /oc-lldp:lldp/oc-lldp:config/oc-lldp:chassis-id-type {
      deviate not-supported;
  }

  // openconfig-vlan

  deviation /oc-vlan:vlans/oc-vlan:vlan/oc-vlan:config/oc-vlan:tpid {
      description
            "Junos does not support tpid configuration in vlan level. It supports it in interface level.";
      deviate not-supported;
  }
  deviation /oc-vlan:vlans/oc-vlan:vlan/oc-vlan:config/oc-vlan:name {
      description
            "Junos does not support tpid configuration in vlan level. It supports it in interface level.";
      deviate add {
          mandatory true;
      }
  }
  deviation /oc-if:interfaces/oc-if:interface/oc-eth:ethernet/oc-vlan:switched-vlan/oc-vlan:config/oc-vlan:access-vlan {
      deviate replace {
          type union {
              type oc-vlan-types:vlan-id;
          }
      }
  }
  deviation /oc-if:interfaces/oc-if:interface/oc-eth:ethernet/oc-vlan:switched-vlan/oc-vlan:config/oc-vlan:native-vlan {
      deviate replace {
          type union {
              type oc-vlan-types:vlan-id;
          }
      }
  }
  deviation /oc-if:interfaces/oc-if:interface/oc-eth:ethernet/oc-vlan:switched-vlan/oc-vlan:config/oc-vlan:trunk-vlans {
      deviate replace {
          type union {
              type oc-vlan-types:vlan-id;
              type oc-vlan-types:vlan-range;
          }
      }
  }

  // NETWORK-INSTANCE Deviations

  deviation /oc-ni:network-instances/oc-ni:network-instance/oc-ni:encapsulation {
      deviate not-supported;
  }

  deviation /oc-ni:network-instances/oc-ni:network-instance/oc-ni:fdb {
      deviate not-supported;
  }

  deviation /oc-ni:network-instances/oc-ni:network-instance/oc-ni:tables {
      deviate not-supported;
  }

  deviation /oc-ni:network-instances/oc-ni:network-instance/oc-ni:vlans {
      deviate not-supported;
  }

  deviation /oc-ni:network-instances/oc-ni:network-instance/oc-ni:table-connections {
      deviate not-supported;
  }

  deviation /oc-ni:network-instances/oc-ni:network-instance/oc-ni:connection-points {
      deviate not-supported;
  }

  deviation /oc-ni:network-instances/oc-ni:network-instance/oc-ni:inter-instance-policies {
      deviate not-supported;
  }

  deviation /oc-ni:network-instances/oc-ni:network-instance/oc-ni:config/oc-ni:enabled-address-families {
      deviate not-supported;
  }

  deviation /oc-ni:network-instances/oc-ni:network-instance/oc-ni:config/oc-ni:mtu {
      deviate not-supported;
  }

  deviation /oc-ni:network-instances/oc-ni:network-instance/oc-ni:config/oc-ni:type {
      description
            "Junos does not support network-instance name without specifying network-instance type.";
      deviate add {
          mandatory true;
      }
  }

  deviation /oc-ni:network-instances/oc-ni:network-instance/oc-ni:protocols/oc-ni:protocol/oc-ni:config/oc-ni:default-metric {
      deviate not-supported;
  }

  deviation /oc-ni:network-instances/oc-ni:network-instance/oc-ni:protocols/oc-ni:protocol/oc-ni:config/oc-ni:enabled {
      deviate not-supported;
  }

  deviation /oc-ni:network-instances/oc-ni:network-instance/oc-ni:protocols/oc-ni:protocol/oc-ni:local-aggregates {
      deviate not-supported;
  }

  deviation /oc-ni:network-instances/oc-ni:network-instance/oc-ni:protocols/oc-ni:protocol/oc-ni:static-routes {
      deviate not-supported;
  }

  deviation /oc-ni:network-instances/oc-ni:network-instance/oc-ni:protocols/oc-ni:protocol {
      description
            "Junos does not support multiple protocol instances in a network-instance.";
      deviate add {
          unique "identifier";
      }
  }

  // ISIS deviation
  deviation  "/oc-ni:network-instances/oc-ni:network-instance/oc-ni:protocols/oc-ni:protocol" +
  "/oc-ni:isis/oc-ni:interfaces/oc-ni:interface/oc-ni:levels/oc-ni:level/oc-ni:adjacencies" +
  "/oc-ni:adjacency/oc-ni:state/oc-ni:neighbor-ipv4-address" {
    description
      "In Junos, ISIS adjacency can have multiple ipv4 address";
    deviate not-supported;
  }

  deviation  "/oc-ni:network-instances/oc-ni:network-instance/oc-ni:protocols/oc-ni:protocol" +
  "/oc-ni:isis/oc-ni:interfaces/oc-ni:interface/oc-ni:levels/oc-ni:level/oc-ni:adjacencies" +
  "/oc-ni:adjacency/oc-ni:state/oc-ni:neighbor-ipv6-address" {
    description
      "In Junos, ISIS adjacency can have multiple ipv6 address";
    deviate not-supported;
  }

  deviation  "/oc-ni:network-instances/oc-ni:network-instance/oc-ni:protocols/oc-ni:protocol" +
  "/oc-ni:isis/oc-ni:levels/oc-ni:level/oc-ni:link-state-database/oc-ni:lsp/oc-ni:tlvs" +
  "/oc-ni:tlv/oc-ni:hostname/oc-ni:state/oc-ni:hostname" {
    description
      "In Junos and according to rfc, hostname can have single value (TLV-137) as the value field identifies the
       symbolic name of the router originating the LSP.";
    deviate not-supported;
  }

  deviation  "/oc-ni:network-instances/oc-ni:network-instance/oc-ni:protocols/oc-ni:protocol" +
  "/oc-ni:isis/oc-ni:levels/oc-ni:level/oc-ni:link-state-database/oc-ni:lsp/oc-ni:tlvs" +
  "/oc-ni:tlv/oc-ni:ipv4-te-router-id/oc-ni:state/oc-ni:router-id" {
    description
      "In Junos and according to rfc, For traffic engineering, it guarantees that we have a
       single stable address that can always be referenced in a path that will be reachable from multiple hops away,
       regardless of the state of the node's interfaces.";

    deviate not-supported;
  }

  deviation  "/oc-ni:network-instances/oc-ni:network-instance/oc-ni:protocols/oc-ni:protocol" +
  "/oc-ni:isis/oc-ni:levels/oc-ni:level/oc-ni:link-state-database/oc-ni:lsp/oc-ni:tlvs" +
  "/oc-ni:tlv/oc-ni:extended-is-reachability/oc-ni:neighbors/oc-ni:neighbor/oc-ni:subtlvs" +
  "/oc-ni:subtlv/oc-ni:adjacency-sids/oc-ni:adjacency-sid" {
    description
      "In Junos and according to rfc, every adjacency-sids subtlv(31) can have only have one adj segment-id.
      For multiple adj segment-ids, multiple adjacency-sids subtlv will be present.
      So it need to be container and not list.";

    deviate not-supported;
  }

  deviation  "/oc-ni:network-instances/oc-ni:network-instance/oc-ni:protocols/oc-ni:protocol" +
  "/oc-ni:isis/oc-ni:levels/oc-ni:level/oc-ni:link-state-database/oc-ni:lsp/oc-ni:tlvs" +
  "/oc-ni:tlv/oc-ni:extended-is-reachability/oc-ni:neighbors/oc-ni:neighbor/oc-ni:subtlvs" +
  "/oc-ni:subtlv/oc-ni:lan-adjacency-sids/oc-ni:lan-adjacency-sid" {
    description
      "In Junos and according to rfc, every lan-adjacency-sids subtlv(32) can have only have one lan-adj segment-id.
      For multiple lan-adj segment-ids, multiple lan-adjacency-sids subtlv will be present.
      So it need to be container and not list.";

    deviate not-supported;
  }

  deviation  "/oc-ni:network-instances/oc-ni:network-instance/oc-ni:protocols/oc-ni:protocol" +
  "/oc-ni:isis/oc-ni:levels/oc-ni:level/oc-ni:link-state-database/oc-ni:lsp/oc-ni:tlvs" +
  "/oc-ni:tlv/oc-ni:mt-isn/oc-ni:neighbors/oc-ni:neighbor/oc-ni:subtlvs" +
  "/oc-ni:subtlv/oc-ni:adjacency-sids/oc-ni:adjacency-sid" {
    description
      "In Junos and according to rfc, every adjacency-sids subtlv(31) can have only have one adj segment-id.
      For multiple adj segment-ids, multiple adjacency-sids subtlv will be present.
      So it need to be container and not list.";

    deviate not-supported;
  }

  deviation  "/oc-ni:network-instances/oc-ni:network-instance/oc-ni:protocols/oc-ni:protocol" +
  "/oc-ni:isis/oc-ni:levels/oc-ni:level/oc-ni:link-state-database/oc-ni:lsp/oc-ni:tlvs" +
  "/oc-ni:tlv/oc-ni:mt-isn/oc-ni:neighbors/oc-ni:neighbor/oc-ni:subtlvs" +
  "/oc-ni:subtlv/oc-ni:lan-adjacency-sids/oc-ni:lan-adjacency-sid" {
    description
      "In Junos and according to rfc, every lan-adjacency-sids subtlv(32) can have only have one lan-adj segment-id.
      For multiple lan-adj segment-ids, multiple lan-adjacency-sids subtlv will be present.
      So it need to be container and not list.";

    deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv6-te-router-id" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:instance-ids" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv6-srlgs" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:purge-oi" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:is-reachability" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv4-internal-reachability" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv4-external-reachability" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:authentication" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:multi-topology" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:isis-neighbor-attribute" {
     
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:mt-isis-neighbor-attribute" {
     
      deviate not-supported;
  }  

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:is-alias-id" {
     
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:mt-isn" {
     
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:mt-ipv4-reachability" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:mt-ipv6-reachability" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:subtlvs/oc-ni:subtlv" +
  "/oc-ni:link-attributes" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:subtlvs/oc-ni:subtlv" +
  "/oc-ni:link-protection-type" {
     
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:subtlvs/oc-ni:subtlv" +
  "/oc-ni:unconstrained-lsp" {
     
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:subtlvs/oc-ni:subtlv" +
  "/oc-ni:link-delay" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:subtlvs/oc-ni:subtlv" +
  "/oc-ni:min-max-link-delay" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:subtlvs/oc-ni:subtlv" +
  "/oc-ni:link-delay-variation" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:subtlvs/oc-ni:subtlv" +
  "/oc-ni:link-loss" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:subtlvs/oc-ni:subtlv" +
  "/oc-ni:residual-bandwidth" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:subtlvs/oc-ni:subtlv" +
  "/oc-ni:available-bandwidth" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:subtlvs/oc-ni:subtlv" +
  "/oc-ni:utilized-bandwidth" {
     
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-ipv4-reachability/oc-ni:prefixes/oc-ni:prefix/oc-ni:subtlvs/oc-ni:subtlv" +
  "/oc-ni:tag64" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-ipv4-reachability/oc-ni:prefixes/oc-ni:prefix/oc-ni:subtlvs/oc-ni:subtlv" +
  "/oc-ni:flags" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-ipv4-reachability/oc-ni:prefixes/oc-ni:prefix/oc-ni:subtlvs/oc-ni:subtlv" +
  "/oc-ni:ipv4-source-router-id" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-ipv4-reachability/oc-ni:prefixes/oc-ni:prefix/oc-ni:subtlvs/oc-ni:subtlv" +
  "/oc-ni:ipv6-source-router-id" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv6-reachability/oc-ni:prefixes/oc-ni:prefix/oc-ni:subtlvs/oc-ni:subtlv" +
  "/oc-ni:tag64" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv6-reachability/oc-ni:prefixes/oc-ni:prefix/oc-ni:subtlvs/oc-ni:subtlv" +
  "/oc-ni:flags" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv6-reachability/oc-ni:prefixes/oc-ni:prefix/oc-ni:subtlvs/oc-ni:subtlv" +
  "/oc-ni:ipv4-source-router-id" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv6-reachability/oc-ni:prefixes/oc-ni:prefix/oc-ni:subtlvs/oc-ni:subtlv" +
  "/oc-ni:ipv6-source-router-id" {

      deviate not-supported;
  } 

  deviation "/oc-ni:network-instances/oc-ni:network-instance/oc-ni:protocols/oc-ni:protocol" +
  "/oc-ni:isis/oc-ni:interfaces/oc-ni:interface/oc-ni:levels/oc-ni:level/oc-ni:packet-counters" {
      description
          "Openconfig needs to update the OC model because the level number of 
           unknown packet-type is not known. And in case of hello packet 
           sent/received in ppmd, only interface information is present and 
           these packets are not sent to rpd from ppmd. Thus, the packet-counters
           are added per interface, instead of per level. The OC version in this
           case is ISIS OC v0.3.3.
          ";
      deviate not-supported;    
  }

  deviation "/oc-ni:network-instances/oc-ni:network-instance/oc-ni:protocols/oc-ni:protocol" +
  "/oc-ni:isis/oc-ni:global" {
      
      deviate not-supported;
  }

  deviation "/oc-ni:network-instances/oc-ni:network-instance/oc-ni:protocols/oc-ni:protocol" +
  "/oc-ni:isis/oc-ni:levels/oc-ni:level/oc-ni:config" {
      
      deviate not-supported;
  }

  deviation "/oc-ni:network-instances/oc-ni:network-instance/oc-ni:protocols/oc-ni:protocol" +
  "/oc-ni:isis/oc-ni:levels/oc-ni:level/oc-ni:state/oc-ni:enabled" {
      
      deviate not-supported;
  }

  deviation "/oc-ni:network-instances/oc-ni:network-instance/oc-ni:protocols/oc-ni:protocol" +
  "/oc-ni:isis/oc-ni:levels/oc-ni:level/oc-ni:state/oc-ni:metric-style" {
      
      deviate not-supported;
  }

  deviation "/oc-ni:network-instances/oc-ni:network-instance/oc-ni:protocols/oc-ni:protocol" +
  "/oc-ni:isis/oc-ni:levels/oc-ni:level/oc-ni:state/oc-ni:authentication-check" {
      
      deviate not-supported;
  }

  deviation "/oc-ni:network-instances/oc-ni:network-instance/oc-ni:protocols/oc-ni:protocol" +
  "/oc-ni:isis/oc-ni:levels/oc-ni:level/oc-ni:traffic-engineering" {
      
      deviate not-supported;
  }

  deviation "/oc-ni:network-instances/oc-ni:network-instance/oc-ni:protocols/oc-ni:protocol" +
  "/oc-ni:isis/oc-ni:levels/oc-ni:level/oc-ni:route-preference" {
      
      deviate not-supported;
  }

  deviation "/oc-ni:network-instances/oc-ni:network-instance/oc-ni:protocols/oc-ni:protocol" +
  "/oc-ni:isis/oc-ni:levels/oc-ni:level/oc-ni:authentication" {
      
      deviate not-supported;
  }

  deviation "/oc-ni:network-instances/oc-ni:network-instance/oc-ni:protocols/oc-ni:protocol" +
  "/oc-ni:isis/oc-ni:interfaces/oc-ni:interface/oc-ni:config" {
      
      deviate not-supported;
  }

  deviation "/oc-ni:network-instances/oc-ni:network-instance/oc-ni:protocols/oc-ni:protocol" +
  "/oc-ni:isis/oc-ni:interfaces/oc-ni:interface/oc-ni:state/oc-ni:enabled" {
     
      deviate not-supported;
  }

  deviation "/oc-ni:network-instances/oc-ni:network-instance/oc-ni:protocols/oc-ni:protocol" +
  "/oc-ni:isis/oc-ni:interfaces/oc-ni:interface/oc-ni:state/oc-ni:passive" {
      
      deviate not-supported;
  }

  deviation "/oc-ni:network-instances/oc-ni:network-instance/oc-ni:protocols/oc-ni:protocol" +
  "/oc-ni:isis/oc-ni:interfaces/oc-ni:interface/oc-ni:state/oc-ni:hello-padding" {
      
      deviate not-supported;
  }

  deviation "/oc-ni:network-instances/oc-ni:network-instance/oc-ni:protocols/oc-ni:protocol" +
  "/oc-ni:isis/oc-ni:interfaces/oc-ni:interface/oc-ni:state/oc-ni:circuit-type" {
      
      deviate not-supported;
  }

  deviation "/oc-ni:network-instances/oc-ni:network-instance/oc-ni:protocols/oc-ni:protocol" +
  "/oc-ni:isis/oc-ni:interfaces/oc-ni:interface/oc-ni:authentication" {
      
      deviate not-supported;
  }

  deviation "/oc-ni:network-instances/oc-ni:network-instance/oc-ni:protocols/oc-ni:protocol" +
  "/oc-ni:isis/oc-ni:interfaces/oc-ni:interface/oc-ni:afi-safi" {
      
      deviate not-supported;
  }

  deviation "/oc-ni:network-instances/oc-ni:network-instance/oc-ni:protocols/oc-ni:protocol" +
  "/oc-ni:isis/oc-ni:interfaces/oc-ni:interface/oc-ni:levels/oc-ni:level/oc-ni:config" {
      
      deviate not-supported;
  }

  deviation "/oc-ni:network-instances/oc-ni:network-instance/oc-ni:protocols/oc-ni:protocol" +
  "/oc-ni:isis/oc-ni:interfaces/oc-ni:interface/oc-ni:levels/oc-ni:level/oc-ni:state" +
  "/oc-ni:passive" {
      
      deviate not-supported;
  }

  deviation "/oc-ni:network-instances/oc-ni:network-instance/oc-ni:protocols/oc-ni:protocol" +
  "/oc-ni:isis/oc-ni:interfaces/oc-ni:interface/oc-ni:levels/oc-ni:level/oc-ni:state" +
  "/oc-ni:priority" {
      
      deviate not-supported;
  }

  deviation "/oc-ni:network-instances/oc-ni:network-instance/oc-ni:protocols/oc-ni:protocol" +
  "/oc-ni:isis/oc-ni:interfaces/oc-ni:interface/oc-ni:levels/oc-ni:level/oc-ni:state" +
  "/oc-ni:enabled" {
      
      deviate not-supported;
  }

  deviation "/oc-ni:network-instances/oc-ni:network-instance/oc-ni:protocols/oc-ni:protocol" +
  "/oc-ni:isis/oc-ni:interfaces/oc-ni:interface/oc-ni:levels/oc-ni:level/oc-ni:timers" {
      
      deviate not-supported;
  }

  deviation "/oc-ni:network-instances/oc-ni:network-instance/oc-ni:protocols/oc-ni:protocol" +
  "/oc-ni:isis/oc-ni:interfaces/oc-ni:interface/oc-ni:levels/oc-ni:level/oc-ni:afi-safi" {
      
      deviate not-supported;
  }

  deviation "/oc-ni:network-instances/oc-ni:network-instance/oc-ni:protocols/oc-ni:protocol" +
  "/oc-ni:isis/oc-ni:interfaces/oc-ni:interface/oc-ni:levels/oc-ni:level" +
  "/oc-ni:hello-authentication" {
      
      deviate not-supported;
  }

  deviation "/oc-ni:network-instances/oc-ni:network-instance/oc-ni:protocols/oc-ni:protocol" +
  "/oc-ni:isis/oc-ni:interfaces/oc-ni:interface/oc-ni:timers" {
      
      deviate not-supported;
  }

  deviation "/oc-ni:network-instances/oc-ni:network-instance/oc-ni:protocols/oc-ni:protocol" +
  "/oc-ni:isis/oc-ni:interfaces/oc-ni:interface/oc-ni:bfd" {
      
      deviate not-supported;
  }

  deviation "/oc-ni:network-instances/oc-ni:network-instance/oc-ni:protocols/oc-ni:protocol" +
  "/oc-ni:isis/oc-ni:interfaces/oc-ni:interface/oc-ni:interface-ref" {
      
      deviate not-supported;
  }


  // Network-Instance - MPLS Deviations
  
  // Global
  deviation /oc-ni:network-instances/oc-ni:network-instance/oc-ni:mpls/oc-ni:global/oc-ni:interface-attributes/oc-ni:interface/oc-ni:interface-ref {
      deviate not-supported;
  }
  // Signaling-Protocols
  deviation /oc-ni:network-instances/oc-ni:network-instance/oc-ni:mpls/oc-ni:signaling-protocols/oc-ni:ldp {
      deviate not-supported;
  }
  deviation /oc-ni:network-instances/oc-ni:network-instance/oc-ni:mpls/oc-ni:signaling-protocols/oc-ni:segment-routing {
      deviate not-supported;
  }

  // Signaling-Protocols - RSVP - Global
  deviation /oc-ni:network-instances/oc-ni:network-instance/oc-ni:mpls/oc-ni:signaling-protocols/oc-ni:rsvp-te/oc-ni:global/oc-ni:hellos/oc-ni:config/oc-ni:hello-interval {
      deviate replace {
          type uint16 {
              range 1..60;
          }
          units seconds;
          default 9;
      }
  }
  deviation /oc-ni:network-instances/oc-ni:network-instance/oc-ni:mpls/oc-ni:signaling-protocols/oc-ni:rsvp-te/oc-ni:global/oc-ni:soft-preemption/oc-ni:config/oc-ni:soft-preemption-timeout {
      deviate replace {
          type uint16 {
              range 1..180;
          }
          default 30;
      }
  }
  deviation /oc-ni:network-instances/oc-ni:network-instance/oc-ni:mpls/oc-ni:signaling-protocols/oc-ni:rsvp-te/oc-ni:global/oc-ni:graceful-restart/oc-ni:config/oc-ni:restart-time {
      deviate replace {
          type uint32 {
              range 1..1800;
          }
      }
  }
  deviation /oc-ni:network-instances/oc-ni:network-instance/oc-ni:mpls/oc-ni:signaling-protocols/oc-ni:rsvp-te/oc-ni:global/oc-ni:graceful-restart/oc-ni:config/oc-ni:recovery-time {
      deviate replace {
          type uint32 {
              range 1..3600;
          }
      }
  }

  // Signaling-Protocols - RSVP - Sessions
  deviation /oc-ni:network-instances/oc-ni:network-instance/oc-ni:mpls/oc-ni:signaling-protocols/oc-ni:rsvp-te/oc-ni:sessions/oc-ni:session/oc-ni:state/oc-ni:local-index {
      deviate replace {
          type uint32;
      }
  }
  
  // Signaling-Protocols - RSVP - Interface Attributes
  deviation /oc-ni:network-instances/oc-ni:network-instance/oc-ni:mpls/oc-ni:signaling-protocols/oc-ni:rsvp-te/oc-ni:interface-attributes/oc-ni:interface/oc-ni:hellos/oc-ni:config/oc-ni:hello-interval {
      deviate replace {
          type uint16 {
              range 1..60;
          }
          units seconds;
          default 9;
      }
  }
  deviation /oc-ni:network-instances/oc-ni:network-instance/oc-ni:mpls/oc-ni:signaling-protocols/oc-ni:rsvp-te/oc-ni:interface-attributes/oc-ni:interface/oc-ni:authentication/oc-ni:config/oc-ni:authentication-key {
      deviate replace {
          type string {
              length 1..16;
          }
      }
  }
  deviation /oc-ni:network-instances/oc-ni:network-instance/oc-ni:mpls/oc-ni:signaling-protocols/oc-ni:rsvp-te/oc-ni:interface-attributes/oc-ni:interface/oc-ni:interface-ref {
      deviate not-supported;
  }

  // TE Global Attributes
  deviation /oc-ni:network-instances/oc-ni:network-instance/oc-ni:mpls/oc-ni:te-global-attributes/oc-ni:srlgs/oc-ni:srlg/oc-ni:config/oc-ni:cost {
      deviate replace {
          type uint32 {
              range 1..65535;
          }
      }
  }
  deviation /oc-ni:network-instances/oc-ni:network-instance/oc-ni:mpls/oc-ni:te-global-attributes/oc-ni:srlgs/oc-ni:srlg/oc-ni:config/oc-ni:value {
      deviate replace {
          type uint32 {
              range 1..max;
          }
      }
  }
  deviation /oc-ni:network-instances/oc-ni:network-instance/oc-ni:mpls/oc-ni:te-global-attributes/oc-ni:srlgs/oc-ni:srlg/oc-ni:config/oc-ni:name {
      deviate replace {
          type string {
              length 1..64;
          }
      }
  }
  deviation /oc-ni:network-instances/oc-ni:network-instance/oc-ni:mpls/oc-ni:te-global-attributes/oc-ni:te-lsp-timers/oc-ni:config/oc-ni:install-delay {
      deviate replace {
          type uint16 {
              range 1..900;
          }
      }
  }
  // TE Interface Attributes
  deviation /oc-ni:network-instances/oc-ni:network-instance/oc-ni:mpls/oc-ni:te-interface-attributes/oc-ni:interface/oc-ni:config/oc-ni:te-metric {
      deviate not-supported;
  }
  deviation /oc-ni:network-instances/oc-ni:network-instance/oc-ni:mpls/oc-ni:te-interface-attributes/oc-ni:interface/oc-ni:igp-flooding-bandwidth/oc-ni:config/oc-ni:threshold-specification {
      deviate not-supported;
  }
  deviation /oc-ni:network-instances/oc-ni:network-instance/oc-ni:mpls/oc-ni:te-interface-attributes/oc-ni:interface/oc-ni:igp-flooding-bandwidth/oc-ni:config/oc-ni:delta-percentage {
      deviate replace {
        type uint8 {
            range 1..20;
        }
      }
  }
  deviation /oc-ni:network-instances/oc-ni:network-instance/oc-ni:mpls/oc-ni:te-interface-attributes/oc-ni:interface/oc-ni:igp-flooding-bandwidth/oc-ni:config/oc-ni:up-thresholds {
      deviate not-supported;
  }
  deviation /oc-ni:network-instances/oc-ni:network-instance/oc-ni:mpls/oc-ni:te-interface-attributes/oc-ni:interface/oc-ni:igp-flooding-bandwidth/oc-ni:config/oc-ni:down-thresholds {
      deviate not-supported;
  }
  deviation /oc-ni:network-instances/oc-ni:network-instance/oc-ni:mpls/oc-ni:te-interface-attributes/oc-ni:interface/oc-ni:igp-flooding-bandwidth/oc-ni:config/oc-ni:up-down-thresholds {
      deviate not-supported;
  }
  deviation /oc-ni:network-instances/oc-ni:network-instance/oc-ni:mpls/oc-ni:te-interface-attributes/oc-ni:interface/oc-ni:interface-ref {
      deviate not-supported;
  }
  // LSPs
  deviation /oc-ni:network-instances/oc-ni:network-instance/oc-ni:mpls/oc-ni:lsps/oc-ni:static-lsps {
      deviate not-supported;
  }
  deviation /oc-ni:network-instances/oc-ni:network-instance/oc-ni:mpls/oc-ni:lsps/oc-ni:unconstrained-path {
      deviate not-supported;
  }
  deviation /oc-ni:network-instances/oc-ni:network-instance/oc-ni:mpls/oc-ni:lsps/oc-ni:constrained-path/oc-ni:named-explicit-paths/oc-ni:named-explicit-path/oc-ni:config/oc-ni:name {
      deviate replace {
          type string {
              length 1..64;
          }
      }
  }
  deviation /oc-ni:network-instances/oc-ni:network-instance/oc-ni:mpls/oc-ni:lsps/oc-ni:constrained-path/oc-ni:tunnels/oc-ni:tunnel/oc-ni:config/oc-ni:name {
      deviate replace {
          type string {
              length 1..64;
          }
      }
  }
  deviation /oc-ni:network-instances/oc-ni:network-instance/oc-ni:mpls/oc-ni:lsps/oc-ni:constrained-path/oc-ni:tunnels/oc-ni:tunnel/oc-ni:config/oc-ni:type {
      deviate not-supported;
  }
  deviation /oc-ni:network-instances/oc-ni:network-instance/oc-ni:mpls/oc-ni:lsps/oc-ni:constrained-path/oc-ni:tunnels/oc-ni:tunnel/oc-ni:config/oc-ni:signaling-protocol {
      deviate not-supported;
  }
  deviation /oc-ni:network-instances/oc-ni:network-instance/oc-ni:mpls/oc-ni:lsps/oc-ni:constrained-path/oc-ni:tunnels/oc-ni:tunnel/oc-ni:config/oc-ni:metric-type {
      deviate not-supported;
  }
  deviation /oc-ni:network-instances/oc-ni:network-instance/oc-ni:mpls/oc-ni:lsps/oc-ni:constrained-path/oc-ni:tunnels/oc-ni:tunnel/oc-ni:config/oc-ni:metric {
      deviate replace {
          type int32 {
              range 1..16777215;
          }
      }
  }
  deviation /oc-ni:network-instances/oc-ni:network-instance/oc-ni:mpls/oc-ni:lsps/oc-ni:constrained-path/oc-ni:tunnels/oc-ni:tunnel/oc-ni:config/oc-ni:shortcut-eligible {
      deviate not-supported;
  }
  deviation /oc-ni:network-instances/oc-ni:network-instance/oc-ni:mpls/oc-ni:lsps/oc-ni:constrained-path/oc-ni:tunnels/oc-ni:tunnel/oc-ni:bandwidth/oc-ni:config/oc-ni:set-bandwidth {
      deviate replace {
          type uint64;
      }
      deviate add {
          units bps;
      }
  }
  deviation /oc-ni:network-instances/oc-ni:network-instance/oc-ni:mpls/oc-ni:lsps/oc-ni:constrained-path/oc-ni:tunnels/oc-ni:tunnel/oc-ni:bandwidth/oc-ni:auto-bandwidth/oc-ni:config/oc-ni:min-bw {
      deviate replace {
          type uint64;
      }
      deviate add {
          units bps;
      }
  }
  deviation /oc-ni:network-instances/oc-ni:network-instance/oc-ni:mpls/oc-ni:lsps/oc-ni:constrained-path/oc-ni:tunnels/oc-ni:tunnel/oc-ni:bandwidth/oc-ni:auto-bandwidth/oc-ni:state/oc-ni:min-bw {
      deviate replace {
          type uint64;
      }
      deviate add {
          units bps;
      }
  }
  deviation /oc-ni:network-instances/oc-ni:network-instance/oc-ni:mpls/oc-ni:lsps/oc-ni:constrained-path/oc-ni:tunnels/oc-ni:tunnel/oc-ni:bandwidth/oc-ni:auto-bandwidth/oc-ni:config/oc-ni:adjust-interval {
      deviate replace {
          type uint32 {
              range 300..315360000;
          }
      }
      deviate add {
          units seconds;
      }
  }
  deviation /oc-ni:network-instances/oc-ni:network-instance/oc-ni:mpls/oc-ni:lsps/oc-ni:constrained-path/oc-ni:tunnels/oc-ni:tunnel/oc-ni:bandwidth/oc-ni:auto-bandwidth/oc-ni:config/oc-ni:adjust-threshold {
      deviate replace {
        type uint8 {
            range 0..50;
        }
      }
  }
  deviation /oc-ni:network-instances/oc-ni:network-instance/oc-ni:mpls/oc-ni:lsps/oc-ni:constrained-path/oc-ni:tunnels/oc-ni:tunnel/oc-ni:bandwidth/oc-ni:auto-bandwidth/oc-ni:config/oc-ni:max-bw {
      deviate replace {
          type uint64;
      }
      deviate add {
          units bps;
      }
  }
  deviation /oc-ni:network-instances/oc-ni:network-instance/oc-ni:mpls/oc-ni:lsps/oc-ni:constrained-path/oc-ni:tunnels/oc-ni:tunnel/oc-ni:bandwidth/oc-ni:auto-bandwidth/oc-ni:state/oc-ni:max-bw {
      deviate replace {
          type uint64;
      }
      deviate add {
          units bps;
      }
  }
  deviation /oc-ni:network-instances/oc-ni:network-instance/oc-ni:mpls/oc-ni:lsps/oc-ni:constrained-path/oc-ni:tunnels/oc-ni:tunnel/oc-ni:bandwidth/oc-ni:auto-bandwidth/oc-ni:overflow/oc-ni:config/oc-ni:overflow-threshold {
      deviate not-supported;
  }
  deviation /oc-ni:network-instances/oc-ni:network-instance/oc-ni:mpls/oc-ni:lsps/oc-ni:constrained-path/oc-ni:tunnels/oc-ni:tunnel/oc-ni:bandwidth/oc-ni:auto-bandwidth/oc-ni:underflow/oc-ni:config/oc-ni:underflow-threshold {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path {
      deviate add {
          max-elements 1;
      }
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:config/oc-ni:cspf-tiebreaker {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:config/oc-ni:path-computation-method {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:config/oc-ni:path-computation-server {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:config/oc-ni:explicit-path-name {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:config/oc-ni:retry-timer {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:state/oc-ni:associated-rsvp-session {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:candidate-secondary-paths {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:config/oc-ni:cspf-tiebreaker {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:config/oc-ni:path-computation-method {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:config/oc-ni:path-computation-server {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:config/oc-ni:explicit-path-name {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:config/oc-ni:retry-timer {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:state/oc-ni:associated-rsvp-session {
      deviate not-supported;
  }

  // JUNOS preference is uint32 [range 0:4294967295]
  deviation /oc-ni:network-instances/oc-ni:network-instance/oc-ni:mpls/oc-ni:lsps/oc-ni:constrained-path/oc-ni:tunnels/oc-ni:tunnel/oc-ni:state/oc-ni:preference {
      deviate replace {
          type uint32; 
      }
  }
  // JUNOS preference is uint32 [range 0:4294967295]
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:state/oc-ni:preference {
      deviate replace {
          type uint32;
      }
  }
  // JUNOS preference is uint32 [range 0:4294967295]
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:state/oc-ni:preference {
      deviate replace {
          type uint32;
      }
  }

  // Network-Instance - BGP Deviations

  // BGP Deviations

  deviation /oc-bgp:bgp {
      description
          "Junos does not support configuting bgp in openconfig-bgp directly must configure through network-instance";
      deviate not-supported;
  }


  deviation /oc-ni:network-instances/oc-ni:network-instance/oc-ni:protocols/oc-ni:protocol/oc-ni:bgp/oc-ni:global/oc-ni:default-route-distance {
      description
          "Junos does not support separate external and internal default-route-distance config knobs."; 
      deviate not-supported;
  }
  deviation /oc-ni:network-instances/oc-ni:network-instance/oc-ni:protocols/oc-ni:protocol/oc-ni:bgp/oc-ni:global/oc-ni:use-multiple-paths {
      description 
          "There is no protocol level config knob for this in Junos.";
      deviate not-supported;
  }
 deviation /oc-ni:network-instances/oc-ni:network-instance/oc-ni:protocols/oc-ni:protocol/oc-ni:bgp/oc-ni:global/oc-ni:afi-safis/oc-ni:afi-safi/oc-ni:route-selection-options/oc-ni:config/oc-ni:advertise-inactive-routes {
      description 
          "In Junos, -advertise-inactive-routes- can not be set per address
           family.";
      deviate not-supported;
  }
  deviation /oc-ni:network-instances/oc-ni:network-instance/oc-ni:protocols/oc-ni:protocol/oc-ni:bgp/oc-ni:global/oc-ni:afi-safis/oc-ni:afi-safi/oc-ni:route-selection-options/oc-ni:config/oc-ni:always-compare-med {
      description 
          "In Junos, -always-compare-med- can not be set per address family.";
      deviate not-supported;
  }
  deviation /oc-ni:network-instances/oc-ni:network-instance/oc-ni:protocols/oc-ni:protocol/oc-ni:bgp/oc-ni:global/oc-ni:afi-safis/oc-ni:afi-safi/oc-ni:route-selection-options/oc-ni:config/oc-ni:external-compare-router-id {
      description 
          "In Junos, -external-compare-router-id- can not be set per address
           family.";
      deviate not-supported;
  }
  deviation /oc-ni:network-instances/oc-ni:network-instance/oc-ni:protocols/oc-ni:protocol/oc-ni:bgp/oc-ni:global/oc-ni:afi-safis/oc-ni:afi-safi/oc-ni:route-selection-options/oc-ni:config/oc-ni:ignore-as-path-length {
      description 
          "In Junos, -ignore-as-path-length- can not be set per address 
           family.";
      deviate not-supported;
  }
  deviation /oc-ni:network-instances/oc-ni:network-instance/oc-ni:protocols/oc-ni:protocol/oc-ni:bgp/oc-ni:global/oc-ni:afi-safis/oc-ni:afi-safi/oc-ni:route-selection-options/oc-ni:config/oc-ni:ignore-next-hop-igp-metric {
      description 
          "There is no BGP specific config knob for this in Junos.";
      deviate not-supported;
  }
  deviation /oc-ni:network-instances/oc-ni:network-instance/oc-ni:protocols/oc-ni:protocol/oc-ni:bgp/oc-ni:global/oc-ni:afi-safis/oc-ni:afi-safi/oc-ni:use-multiple-paths {
      description 
          "In Junos, -multipath- config cannot be set per address family.";
      deviate not-supported;
  }
  deviation /oc-ni:network-instances/oc-ni:network-instance/oc-ni:protocols/oc-ni:protocol/oc-ni:bgp/oc-ni:global/oc-ni:afi-safis/oc-ni:afi-safi/oc-ni:ipv4-unicast/oc-ni:config/oc-ni:send-default-route {
      description 
          "There is no BGP specific config knob for this in Junos.";
      deviate not-supported;
  }
  deviation /oc-ni:network-instances/oc-ni:network-instance/oc-ni:protocols/oc-ni:protocol/oc-ni:bgp/oc-ni:global/oc-ni:afi-safis/oc-ni:afi-safi/oc-ni:ipv6-unicast/oc-ni:config/oc-ni:send-default-route {
      description 
          "There is no BGP specific config knob for this in Junos.";
      deviate not-supported;
  }
 deviation /oc-ni:network-instances/oc-ni:network-instance/oc-ni:protocols/oc-ni:protocol/oc-ni:bgp/oc-ni:peer-groups/oc-ni:peer-group/oc-ni:config/oc-ni:send-community {
      description 
          "There is no BGP specific config knob for this in Junos.";
      deviate not-supported;
  }
  deviation /oc-ni:network-instances/oc-ni:network-instance/oc-ni:protocols/oc-ni:protocol/oc-ni:bgp/oc-ni:peer-groups/oc-ni:peer-group/oc-ni:timers/oc-ni:config/oc-ni:keepalive-interval {
      description 
          "In Junos, the keepalive-interval is always 1/3 hold-time.";
      deviate not-supported;
  }
  deviation /oc-ni:network-instances/oc-ni:network-instance/oc-ni:protocols/oc-ni:protocol/oc-ni:bgp/oc-ni:peer-groups/oc-ni:peer-group/oc-ni:as-path-options/oc-ni:config/oc-ni:disable-peer-as-filter {
      description
          "There is no BGP specific config knob at the peer-group level for this in Junos.";
      deviate not-supported;
  }
  deviation /oc-ni:network-instances/oc-ni:network-instance/oc-ni:protocols/oc-ni:protocol/oc-ni:bgp/oc-ni:peer-groups/oc-ni:peer-group/oc-ni:afi-safis/oc-ni:afi-safi/oc-ni:add-paths/oc-ni:config/oc-ni:send-max {
      deviate replace {
          type uint8 {
              range 2..6;
          }
      }  
   }
  deviation /oc-ni:network-instances/oc-ni:network-instance/oc-ni:protocols/oc-ni:protocol/oc-ni:bgp/oc-ni:peer-groups/oc-ni:peer-group/oc-ni:afi-safis/oc-ni:afi-safi/oc-ni:add-paths/oc-ni:config/oc-ni:send {
      deviate add {
          must '(. == "false" or send-max)' {
           error-message
             "When 'send' is true, send-max must be configured.";
          }
      }  
   }
  deviation /oc-ni:network-instances/oc-ni:network-instance/oc-ni:protocols/oc-ni:protocol/oc-ni:bgp/oc-ni:peer-groups/oc-ni:peer-group/oc-ni:afi-safis/oc-ni:afi-safi/oc-ni:use-multiple-paths {
      description 
          "In Junos, -multipath- config cannot be set per address family.";
      deviate not-supported;
  }
  deviation /oc-ni:network-instances/oc-ni:network-instance/oc-ni:protocols/oc-ni:protocol/oc-ni:bgp/oc-ni:peer-groups/oc-ni:peer-group/oc-ni:afi-safis/oc-ni:afi-safi/oc-ni:apply-policy {
      description 
          "In Junos, import/export policies cannot be applied per address 
           family.";
      deviate not-supported;
  }
  deviation /oc-ni:network-instances/oc-ni:network-instance/oc-ni:protocols/oc-ni:protocol/oc-ni:bgp/oc-ni:peer-groups/oc-ni:peer-group/oc-ni:afi-safis/oc-ni:afi-safi/oc-ni:ipv4-unicast/oc-ni:prefix-limit/oc-ni:config/oc-ni:prevent-teardown {
      deviate add {
          must '(. == "true" or max-prefix)' {
           error-message
             "When 'prevent-teardown' is true, max-prefix must be configured.";
          }
      }  
   }
  deviation /oc-ni:network-instances/oc-ni:network-instance/oc-ni:protocols/oc-ni:protocol/oc-ni:bgp/oc-ni:peer-groups/oc-ni:peer-group/oc-ni:afi-safis/oc-ni:afi-safi/oc-ni:ipv4-unicast/oc-ni:config/oc-ni:send-default-route {
      description 
          "There is no BGP specific config knob for this in Junos.";
      deviate not-supported;
  }
  deviation /oc-ni:network-instances/oc-ni:network-instance/oc-ni:protocols/oc-ni:protocol/oc-ni:bgp/oc-ni:peer-groups/oc-ni:peer-group/oc-ni:apply-policy/oc-ni:config/oc-ni:default-import-policy {
      description 
          "In Junos, the default-policy is the one at the end of the 
           policy-chain.";
      deviate not-supported;
  }
  deviation /oc-ni:network-instances/oc-ni:network-instance/oc-ni:protocols/oc-ni:protocol/oc-ni:bgp/oc-ni:peer-groups/oc-ni:peer-group/oc-ni:apply-policy/oc-ni:config/oc-ni:default-export-policy {
      description 
          "In Junos, the default-policy is the one at the end of the 
           policy-chain.";
      deviate not-supported;
  }
  deviation /oc-ni:network-instances/oc-ni:network-instance/oc-ni:protocols/oc-ni:protocol/oc-ni:bgp/oc-ni:peer-groups/oc-ni:peer-group/oc-ni:afi-safis/oc-ni:afi-safi/oc-ni:ipv6-unicast/oc-ni:config/oc-ni:send-default-route {
      description 
          "There is no BGP specific config knob for this in Junos.";
      deviate not-supported;
  }
  deviation /oc-ni:network-instances/oc-ni:network-instance/oc-ni:protocols/oc-ni:protocol/oc-ni:bgp/oc-ni:neighbors/oc-ni:neighbor/oc-ni:config/oc-ni:neighbor-address {
      deviate replace {
          type inet:ip-address;
      }
  }
  deviation /oc-ni:network-instances/oc-ni:network-instance/oc-ni:protocols/oc-ni:protocol/oc-ni:bgp/oc-ni:neighbors/oc-ni:neighbor/oc-ni:transport/oc-ni:state/oc-ni:remote-address {
      deviate replace {
          type inet:ip-address;
      }
  }
  deviation /oc-ni:network-instances/oc-ni:network-instance/oc-ni:protocols/oc-ni:protocol/oc-ni:bgp/oc-ni:neighbors/oc-ni:neighbor/oc-ni:config/oc-ni:send-community {
      description 
          "There is no BGP specific config knob for this in Junos.";
      deviate not-supported;
  }
  deviation /oc-ni:network-instances/oc-ni:network-instance/oc-ni:protocols/oc-ni:protocol/oc-ni:bgp/oc-ni:neighbors/oc-ni:neighbor/oc-ni:timers/oc-ni:config/oc-ni:keepalive-interval {
      description 
          "In Junos, the keepalive-interval is always 1/3 hold-time.";
      deviate not-supported;
  }
  deviation /oc-ni:network-instances/oc-ni:network-instance/oc-ni:protocols/oc-ni:protocol/oc-ni:bgp/oc-ni:neighbors/oc-ni:neighbor/oc-ni:afi-safis/oc-ni:afi-safi/oc-ni:add-paths/oc-ni:config/oc-ni:send-max {
      deviate replace {
          type uint8 {
              range 2..6;
          }
      }  
   }
  deviation /oc-ni:network-instances/oc-ni:network-instance/oc-ni:protocols/oc-ni:protocol/oc-ni:bgp/oc-ni:neighbors/oc-ni:neighbor/oc-ni:afi-safis/oc-ni:afi-safi/oc-ni:add-paths/oc-ni:config/oc-ni:send {
      deviate add {
           must '(. = "false" or ../send-max )' {
           error-message
             "When 'send' is true, send-max must be configured.";
          }
      }  
   }
  deviation /oc-ni:network-instances/oc-ni:network-instance/oc-ni:protocols/oc-ni:protocol/oc-ni:bgp/oc-ni:neighbors/oc-ni:neighbor/oc-ni:afi-safis/oc-ni:afi-safi/oc-ni:use-multiple-paths {
      description 
          "In Junos, -multipath- config cannot be set per address family.";
      deviate not-supported;
  }
  deviation /oc-ni:network-instances/oc-ni:network-instance/oc-ni:protocols/oc-ni:protocol/oc-ni:bgp/oc-ni:neighbors/oc-ni:neighbor/oc-ni:afi-safis/oc-ni:afi-safi/oc-ni:apply-policy {
      description 
          "In Junos, import/export policies cannot be applied per address 
           family.";
      deviate not-supported;
  }
  deviation /oc-ni:network-instances/oc-ni:network-instance/oc-ni:protocols/oc-ni:protocol/oc-ni:bgp/oc-ni:neighbors/oc-ni:neighbor/oc-ni:afi-safis/oc-ni:afi-safi/oc-ni:ipv4-unicast/oc-ni:prefix-limit/oc-ni:config/oc-ni:prevent-teardown {
      deviate add {
          must '(. == "true" or max-prefix)' {
           error-message
             "When 'prevent-teardown' is true, max-prefix must be configured.";
          }
      }  
   }
  deviation /oc-ni:network-instances/oc-ni:network-instance/oc-ni:protocols/oc-ni:protocol/oc-ni:bgp/oc-ni:neighbors/oc-ni:neighbor/oc-ni:afi-safis/oc-ni:afi-safi/oc-ni:ipv6-unicast/oc-ni:prefix-limit/oc-ni:config/oc-ni:prevent-teardown {
      deviate add {
          must '(. == "true" or max-prefix)' {
           error-message
             "When 'prevent-teardown' is true, max-prefix must be configured.";
          }
      }  
   }
  deviation /oc-ni:network-instances/oc-ni:network-instance/oc-ni:protocols/oc-ni:protocol/oc-ni:bgp/oc-ni:neighbors/oc-ni:neighbor/oc-ni:afi-safis/oc-ni:afi-safi/oc-ni:ipv4-unicast/oc-ni:config/oc-ni:send-default-route {
      description 
          "There is no BGP specific config knob for this in Junos.";
      deviate not-supported;
  }
  deviation /oc-ni:network-instances/oc-ni:network-instance/oc-ni:protocols/oc-ni:protocol/oc-ni:bgp/oc-ni:neighbors/oc-ni:neighbor/oc-ni:afi-safis/oc-ni:afi-safi/oc-ni:ipv6-unicast/oc-ni:config/oc-ni:send-default-route {
      description 
          "There is no BGP specific config knob for this in Junos.";
      deviate not-supported;
  }
  deviation /oc-ni:network-instances/oc-ni:network-instance/oc-ni:protocols/oc-ni:protocol/oc-ni:bgp/oc-ni:neighbors/oc-ni:neighbor/oc-ni:apply-policy/oc-ni:config/oc-ni:default-import-policy {
      description 
          "In Junos, the default-policy is the one at the end of the 
           policy-chain.";
      deviate not-supported;
  }
  deviation /oc-ni:network-instances/oc-ni:network-instance/oc-ni:protocols/oc-ni:protocol/oc-ni:bgp/oc-ni:neighbors/oc-ni:neighbor/oc-ni:apply-policy/oc-ni:config/oc-ni:default-export-policy {
      description 
          "In Junos, the default-policy is the one at the end of the 
           policy-chain.";
      deviate not-supported;
  }
}
