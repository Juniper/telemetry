module jnx-aug-openconfig-aft {    
    yang-version "1";

    // namespace
    namespace "http://yang.juniper.net/openconfig/augment/aft";

    prefix "jnx-oc-aft";

    import openconfig-network-instance { prefix oc-ni; }

    // meta
    organization "Juniper Networks";

    description "This module contains augments to openconfig afts";

    revision "2019-02-15" {
	description "None";
    }

    augment "/oc-ni:network-instances/oc-ni:network-instance/oc-ni:afts/oc-ni:next-hops/oc-ni:next-hop" {
	container juniper {
	    container state {
		leaf unmapped-nexthop {
		    type boolean;
		}
		leaf-list mapped-next-hop-index {
		    type uint64;
		}
	    }
	}
    }
}
