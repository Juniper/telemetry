/*
 * $Id$
 *
 * Copyright (c) 2006-2020, Juniper Networks, Inc.
 * All rights reserved.
 *
 */

module pfe_page_drop_oc {

  yang-version "1";

  // namespace
  namespace "http://juniper.net/yang/pfepagedrop";

  prefix "pfe-page-drop-oc";

  import drend { prefix dr; }
  import jnpr-proto { prefix jnpr-proto; }
  import junos-page-drop-stats { prefix junos-page-drop; }
  jnpr-proto:message-id "PFE-PAGE-DROP-OC-MESSAGE-ID";

  // meta
  organization "Juniper Network Inc.";

  contact "www.juniper.net";

  grouping pfe-page-drop {
      uses junos-page-drop:pfe-page-drop {
      augment "junos/system" {
        dr:source "/junos/system/linecard/page-drops/page-drop/";
        dr:fieldnum 151;
      }
      augment "junos/system/linecard" {
        dr:source "/junos/system/linecard/page-drops/page-drop/";
        dr:fieldnum 151;
      }
      augment "junos/system/linecard/page-drops" {
        dr:source "/junos/system/linecard/page-drops/page-drop/";
        dr:fieldnum 151;
      }
      augment "junos/system/linecard/page-drops/page-drop" {
        dr:source "/junos/system/linecard/page-drops/page-drop/";
        dr:fieldnum 152;
      }
      augment "junos/system/linecard/page-drops/page-drop/pfe" {
        dr:source "/junos/system/linecard/page-drops/page-drop/";
        dr:fieldnum 51;
      }
      augment "junos/system/linecard/page-drops/page-drop/count" {
        dr:source "/junos/system/linecard/page-drops/page-drop/";
        dr:fieldnum 52;
      }
      augment "junos/system/linecard/page-drops/page-drop/interface" {
        dr:source "/junos/system/linecard/page-drops/page-drop/";
        dr:fieldnum 53;
      }
      augment "junos/system/linecard/page-drops/page-drop/interface-oq" {
        dr:source "/junos/system/linecard/page-drops/page-drop/";
        dr:fieldnum 54;
      }
      augment "junos/system/linecard/page-drops/page-drop/interface-parent-ae" {
        dr:source "/junos/system/linecard/page-drops/page-drop/";
        dr:fieldnum 55;
      }
    }
  }

  dr:command-app "agentd";
  rpc juniper-netconf-get {
    output {
        uses pfe-page-drop;
    }
  }
}
