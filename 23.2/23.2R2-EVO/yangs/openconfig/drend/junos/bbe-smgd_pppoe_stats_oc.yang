/*
    * OC definition for pppoe stats
    *
    * Copyright (c) 2017, Juniper Networks, Inc.
    * All rights reserved.
*/

/**
  * @file
  * OC Render Tree.
*/

module bbe-smgd_pppoe_stats_oc {
    yang-version "1";
    namespace "http://juniper.net/yang/bbe-smgd_pppoe_stats_oc";
    prefix "bbe-smgd_pppoe_stats_oc";
    import drend {
        prefix "dr";
    }
    import jnpr-proto { prefix jnpr-proto; }
   
    /*
     * Daemon socket that handles this hierarchy
     */	 

    dr:command-app "smg-service";
    dr:sub-component "pppoe-stats";
    jnpr-proto:message-id "BBE-SMGD-PPPOE-STATS-OC-MESSAGE-ID";

    grouping pppoe-stats-group {
        description "The set of statistics associated with the PPPoE protocol module";
        leaf padi-packets-sent {
            description "The number of PPPoE Active Discovery Initiation (PADI) packets transmitted by the PPPoE protocol module";
            type uint32;
            dr:source padi-packets-sent;
            dr:fieldnum 51;
        }
        leaf padi-packets-received {
            description "The number of PPPoE Active Discovery Initiation (PADI) packets received by the PPPoE protocol module";
            type uint32;
            dr:source padi-packets-received;
            dr:fieldnum 52;
        }
        leaf pado-packets-sent {
            description "The number of PPPoE Active Discovery Offer (PADO) packets transmitted by the PPPoE protocol module";
            type uint32;
            dr:source pado-packets-sent;
            dr:fieldnum 53;
        }
        leaf pado-packets-received {
            description "The number of PPPoE Active Discovery Offer (PADO) packets received by the PPPoE protocol module";
            type uint32;
            dr:source pado-packets-received;
            dr:fieldnum 54;
        }
        leaf padr-packets-sent {
            description "The number of PPPoE Active Discovery Request (PADR) packets transmitted by the PPPoE protocol module";
            type uint32;
            dr:source padr-packets-sent;
            dr:fieldnum 55;
        }
        leaf padr-packets-received {
            description "The number of PPPoE Active Discovery Request (PADR) packets received by the PPPoE protocol module";
            type uint32;
            dr:source padr-packets-received;
            dr:fieldnum 56;
        }
        leaf pads-packets-sent {
            description "The number of PPPoE Active Discovery Session-Confirmation (PADS) packets transmitted by the PPPoE protocol module";
            type uint32;
            dr:source pads-packets-sent;
            dr:fieldnum 57;
        }
        leaf pads-packets-received {
            description "The number of PPPoE Active Discovery Session-Confirmation (PADS) packets received by the PPPoE protocol module";
            type uint32;
            dr:source pads-packets-received;
            dr:fieldnum 58;
        }
        leaf padt-packets-sent {
            description "The number of PPPoE Active Discovery Terminate (PADT) packets transmitted by the PPPoE protocol module";
            type uint32;
            dr:source padt-packets-sent;
            dr:fieldnum 59;
        }
        leaf padt-packets-received {
            description "The number of PPPoE Active Discovery Terminate (PADT) packets received by the PPPoE protocol module";
            type uint32;
            dr:source padt-packets-received;
            dr:fieldnum 60;
        }
        leaf service-error-sent {
            description "The number of PPPoE service error packets transmitted by the PPPoE protocol module";
            type uint32;
            dr:source service-error-sent;
            dr:fieldnum 61;
        }
        leaf service-error-received {
            description "The number of PPPoE service error packets received by the PPPoE protocol module";
            type uint32;
            dr:source service-error-received;
            dr:fieldnum 62;
        }
        leaf ac-error-sent {
            description "The number of PPPoE ac error packets transmitted by the PPPoE protocol module";
            type uint32;
            dr:source ac-error-sent;
            dr:fieldnum 63;
        }
        leaf ac-error-received {
            description "The number of PPPoE ac error packets received by the PPPoE protocol module";
            type uint32;
            dr:source ac-error-received;
            dr:fieldnum 64;
        }
        leaf generic-error-sent {
            description "The number of PPPoE generic error packets transmitted by the PPPoE protocol module";
            type uint32;
            dr:source generic-error-sent;
            dr:fieldnum 65;
        }
        leaf generic-error-received {
            description "The number of PPPoE generic error packets received by the PPPoE protocol module";
            type uint32;
            dr:source generic-error-received;
            dr:fieldnum 66;
        }
        leaf malformed-packets-received {
            description "The number of PPPoE malformed packets received by the PPPoE protocol module";
            type uint32;
            dr:source malformed-packets-received;
            dr:fieldnum 67;
        }
        leaf unknown-packets-received {
            description "The number of PPPoE unknown packets received by the PPPoE protocol module";
            type uint32;
            dr:source unknown-packets-received;
            dr:fieldnum 68;
        }
        leaf era-inflight-count {
            description "The count of in-flight PPPoE sessions reported to the Event Rate Analyzer (ERA)";
            type uint32;
            dr:source era-inflight-count;
            dr:fieldnum 69;
        }
        leaf era-reported-successes {
            description "The count of successful PPPoE sessions reported to the Event Rate Analyzer (ERA)";
            type uint32;
            dr:source era-reported-successes;
            dr:fieldnum 70;
        }
        leaf era-reported-failures {
            description "The count of failed PPPoE sessions reported to the Event Rate Analyzer (ERA)";
            type uint32;
            dr:source era-reported-failures;
            dr:fieldnum 71;
        }
    }
    rpc juniper-netconf-get {
        dr:command-top-of-output "/oc-bbe-smgd-information";
        dr:command-help "Default <get> rpc";
        output {
            container junos {
                container system {
		    dr:fieldnum 151;
                    container subscriber-management {
			dr:fieldnum 151;
                        container client-protocols {
			    dr:fieldnum 151;
                            container pppoe {
				dr:fieldnum 151;
                                container statistics {
                                    dr:source "/junos/system/subscriber-management/client-protocols/pppoe/statistics";
				    dr:fieldnum 151;
                                    uses pppoe-stats-group;
                                }
                            }
                        }
                    }
                }
            }
        }
    }
}
