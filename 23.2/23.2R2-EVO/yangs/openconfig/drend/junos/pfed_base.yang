/*
 * $Id:$
 *
 * Copyright (c) 2016, Juniper Networks, Inc.
 * All rights reserved.
 */

module pfed_base {
  yang-version "1";

  // namespace
  namespace "http://juniper.net/yang/pfedbase";

  prefix "pfedbase";

  import drend {
     prefix "dr";
  }
  import jnpr-proto { prefix jnpr-proto; }


  dr:command-app "pfed";
  dr:sub-component "pfe-base";
  jnpr-proto:message-id "PFED-BASE-MESSAGE-ID";

  grouping pfed-base {
   container junos {
   list npu-memory {
     key pfe-name;
        leaf pfe-name {
           type string;
        }
        leaf combined-pool-name {
           type string;
        }
        leaf combined-size {
           type uint32;
        }
        leaf combined-usage-count {
           type uint32;
        }
        leaf combined-utilization {
           type uint32;
        }
        leaf global-pool-name {
           type string;
        }
        leaf global-usage-count {
           type uint32;
        }
        leaf global-alloc-count {
           type uint32;
        }
        leaf global-free-count {
           type uint32;
        }
        leaf local-pool-name {
           type string;
        }
        leaf local-usage-count {
           type uint32;
        }
        leaf local-alloc-count {
           type uint32;
        }
        leaf local-free-count {
           type uint32;
        }
     }
   }
  }

  uses pfed-base;
}
