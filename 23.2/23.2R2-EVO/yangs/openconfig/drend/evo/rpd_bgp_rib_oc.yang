/*
 * Render tree for BGP RIB Openconfig *
 * November 2017, Lynne Morrison
 *
 * Copyright (c) 1998-2023, Juniper Networks, Inc.
 * All rights reserved.
 */

/**
 * @file
 * BGP RIB Render Tree.
 */

module rpd_bgp_rib_oc {
  yang-version "1";

  // namespace
  namespace "http://juniper.net/yang/bgp_rib_oc_render";

  prefix "bgpriboc";

  import drend {
    prefix "dr";
  }
  import jnpr-proto { prefix jnpr-proto; }
  import openconfig-inet-types { prefix oc-inet; }
  import openconfig-rib-bgp {prefix oc-bgprib; }


  description "
    Rendering Junos BGP routing table (RIB) in Openconfig BGP RIB Schema terms
  ";

  revision "2016-04-11" {
    description
      "OpenConfig public release";
    reference "0.2.0";
  }

  /*
   * Daemon that handles this hierarchy
   */
  dr:command-app "rpd";
  dr:sub-component "bgp-rib";
  jnpr-proto:message-id "RPD-BGP-RIB-OC-MESSAGE-ID";


  grouping rend-bgp-shared-common-attr-state {
    uses oc-bgprib:bgp-shared-common-attr-state {
      augment origin {
        dr:source "attr-origin";
        dr:fieldnum 52;
        dr:map IGP { dr:map-from 0; }
        dr:map EGP { dr:map-from 1; }
        dr:map INCOMPLETE { dr:map-from 2; }
      }

      augment atomic-aggregate {
        dr:source "attr-atomic-aggr";
        dr:fieldnum 53;
      }

      augment next-hop {
        dr:source "attr-next-hop";
        dr:fieldnum 54;
      }

      augment med {
        dr:source "attr-med";
        dr:fieldnum 55;
      }

      augment local-pref {
        dr:source "attr-local-pref";
        dr:fieldnum 56;
      }

      augment originator-id {
        dr:source "attr-originator-id";
        dr:fieldnum 57;
      }

      augment cluster-list {
        dr:source "attr-cluster-list";
        dr:fieldnum 58;
      }

      augment aigp {
        dr:source "attr-aigp";
        dr:fieldnum 59;
      }
    }
  }

  grouping rend-bgp-aggregator-attr-top {
    uses oc-bgprib:bgp-aggregator-attr-top {
      augment aggregator {
        dr:fieldnum 152;
      }

      augment aggregator/state {
        dr:fieldnum 151;
      }

      augment aggregator/state/as {
        dr:source "attr-aggregator-as";
        dr:fieldnum 51;
      }

      augment aggregator/state/as4 {
        dr:source "attr-aggregator-as4";
        dr:fieldnum 52;
      }

      augment aggregator/state/address {
        dr:source "attr-aggregator-address";
        dr:fieldnum 53;
      }
    }
  }

  grouping rend-bgp-as-path-attr-top {
    uses oc-bgprib:bgp-as-path-attr-top {
      augment as-path {
        dr:fieldnum 153;
      }

      augment as-path/as-segment {
        dr:source attr-as-path-segments;
        dr:fieldnum 151;
      }

      augment as-path/as-segment/state {
        dr:fieldnum 151;
      }

      augment as-path/as-segment/state/type {
        dr:source "attr-as-segment-type";
        dr:map AS_SEQ { dr:map-from 2; }
        dr:map AS_SET { dr:map-from 1; }
        dr:map AS_CONFED_SEQUENCE { dr:map-from 3; }
        dr:map AS_CONFED_SET { dr:map-from 4; }
        dr:fieldnum 51;
      }

      augment as-path/as-segment/state/member {
        dr:source "attr-as-segment-member";
        dr:fieldnum 52;
      }
    }
  }

  grouping rend-bgp-as4-path-attr-top {
    uses oc-bgprib:bgp-as4-path-attr-top {
      augment as4-path {
        dr:fieldnum 154;
      }

      augment as4-path/as4-segment {
        dr:source attr-as4-path-segments;
        dr:fieldnum 151;
      }

      augment as4-path/as4-segment/state {
        dr:fieldnum 151;
      }

      augment as4-path/as4-segment/state/type {
        dr:source "attr-as4-segment-type";
        dr:map AS_SEQ { dr:map-from 2; }
        dr:map AS_SET { dr:map-from 1; }
        dr:map AS_CONFED_SEQUENCE { dr:map-from 3; }
        dr:map AS_CONFED_SET { dr:map-from 4; }
        dr:fieldnum 51;
      }

      augment as4-path/as4-segment/state/member {
        dr:source "attr-as4-segment-member";
        dr:fieldnum 52;
      }
    }
  }

  grouping rend-attr-sets-top {
    container attr-sets {
      dr:source "attr-sets";
      dr:fieldnum 151;

      list attr-set {
        dr:source "attr-set";
        dr:fieldnum 151;
        key index;
        dr:atomic-data;

        leaf index {
          type uint64;
          dr:source "attr-set-index";
          dr:fieldnum 51;
        }

        container state {
          dr:fieldnum 151;

          leaf index {
            type uint64;
            dr:source "attr-set-index";
            dr:fieldnum 51;
          }

          uses rend-bgp-shared-common-attr-state;
        }

        uses rend-bgp-aggregator-attr-top;
        uses rend-bgp-as-path-attr-top;
        uses rend-bgp-as4-path-attr-top;
      }
    }
  }

  grouping rend-community-sets-top {
    uses oc-bgprib:community-sets-top {
      augment communities {
        dr:source "communities";
        dr:fieldnum 152;
      }

      augment communities/community {
        dr:source "community-list";
        dr:fieldnum 151;
        dr:atomic-data;
      }

      augment communities/community/index {
        dr:source "comm-index";
        dr:fieldnum 51;
      }

      augment communities/community/state {
        dr:fieldnum 151;
      }

      augment communities/community/state/index {
        dr:source "comm-index";
        dr:fieldnum 51;
      }

      augment communities/community/state/community {
        dr:source "community";
        dr:fieldnum 52;
      }
    }
  }

  grouping rend-ext-community-sets-top {
    uses oc-bgprib:ext-community-sets-top {
      augment ext-communities {
        dr:source "ext-communities";
        dr:fieldnum 153;
      }

      augment ext-communities/ext-community {
        dr:source "ext-community-list";
        dr:fieldnum 151;
        dr:atomic-data;
      }

      augment ext-communities/ext-community/index {
        dr:source "ext-comm-index";
        dr:fieldnum 51;
      }

      augment ext-communities/ext-community/state {
        dr:fieldnum 151;
      }

      augment ext-communities/ext-community/state/index {
        dr:source "ext-comm-index";
        dr:fieldnum 51;
      }

      augment ext-communities/ext-community/state/ext-community {
        dr:source "ext-community";
        dr:fieldnum 52;
      }
    }
  }

  grouping rend-bgp-rib-state {
    uses oc-bgprib:bgp-rib-state {
      augment afi-safi-name {
        dr:source "rib-name";
        dr:fieldnum 51;
        dr:map IPV4_UNICAST {dr:map-from inet.0; }
        dr:map IPV6_UNICAST {dr:map-from inet6.0; }
        dr:map L2VPN_EVPN { dr:map-from inst.evpn.0; }
      }
    }
  }

  grouping rend-loc-rib-keys {
    uses oc-bgprib:bgp-loc-rib-common-keys {
      augment "origin" {
        dr:source "attributes-origin";
        dr:fieldnum 52;
        dr:map IGP { dr:map-from 0; }
        dr:map EGP { dr:map-from 1; }
        dr:map INCOMPLETE { dr:map-from 2; }
      }

      augment "path-id" {
        dr:source "path-id";
        dr:fieldnum 53;
      }
    }
  }

  grouping rend-v4-loc-rib-keys {
    leaf "prefix" {
      type oc-inet:ipv4-prefix;
      dr:source "prefix";
      dr:fieldnum 51;
    }

    uses rend-loc-rib-keys;
  }

  grouping rend-v6-loc-rib-keys {
    leaf "prefix" {
      type oc-inet:ipv6-prefix;
      dr:source "prefix";
      dr:fieldnum 51;
    }

    uses rend-loc-rib-keys;
  }

  grouping rend-loc-rib-common-attr-refs {
    uses oc-bgprib:bgp-loc-rib-common-attr-refs {
      augment attr-index {
        dr:source "attr-index";
        dr:fieldnum 54;
      }
       augment community-index {
        dr:source "comm-index";
        dr:fieldnum 55;
      }
       augment ext-community-index {
        dr:source "ext-comm-index";
        dr:fieldnum 56;
      }
    }
  }

  grouping rend-bgp-common-route-annotations-state {
    uses oc-bgprib:bgp-common-route-annotations-state {
      augment "last-modified" {
        dr:source "last-modified-date";
        dr:fieldnum 57;
      }

      augment "valid-route" {
        dr:source "valid-route";
        dr:fieldnum 58;
      }

      augment "invalid-reason" {
        dr:map INVALID_CLUSTER_LOOP { dr:map-from 3; }
        dr:map INVALID_AS_LOOP      { dr:map-from 5; }
        dr:map INVALID_ORIGINATOR   { dr:map-from 6; }
        dr:map INVALID_CONFED       { dr:map-from 4; }
        dr:source "invalid-reason";
        dr:fieldnum 59;
      }
    }
  }

  grouping rend-bgp-unknown-attr-flags-state {
    uses oc-bgprib:bgp-unknown-attr-flags-state {
      augment "optional" {
        dr:source "optional";
        dr:fieldnum 51;
      }
      augment "transitive" {
        dr:source "transitive";
        dr:fieldnum 52;
      }
      augment "partial" {
        dr:source "partial";
        dr:fieldnum 53;
      }
      augment "extended" {
        dr:source "extended";
        dr:fieldnum 54;
      }
    }
  }

  grouping rend-bgp-unknown-attr-state {
    uses oc-bgprib:bgp-unknown-attr-state {
      augment "attr-type" {
        dr:source "attr-type";
        dr:fieldnum 61;
      }
      augment "attr-len" {
        dr:source "attr-len";
        dr:fieldnum 62;
      }
      augment "attr-value" {
        dr:source "attr-val";
        dr:fieldnum 63;
      }
    }
  }

  grouping rend-bgp-unknown-attr-top {
    container unknown-attributes {
      dr:fieldnum 162;

      list unknown-attribute {
        dr:source "unknown-attributes";
        dr:fieldnum 171;
        key "attr-type";
        leaf "attr-type" {
          type uint8;
          dr:source "attr-type";
          dr:fieldnum 51;
        }

        container state {
          dr:fieldnum 181;
          uses rend-bgp-unknown-attr-flags-state;
          uses rend-bgp-unknown-attr-state;
        }
      }
    }
  }

  grouping rend-v4-loc-rib-routes-top {
    container routes {
      dr:fieldnum 151;

      list route {
        dr:source "route";
        dr:fieldnum 151;
        dr:atomic-data;
        key "prefix origin path-id";

        uses rend-v4-loc-rib-keys;

        container state {
          dr:fieldnum 151;

          uses rend-v4-loc-rib-keys;
          uses rend-loc-rib-common-attr-refs;
          uses rend-bgp-common-route-annotations-state;

        }
        uses rend-bgp-unknown-attr-top;
      }
    }
  }

  grouping rend-v6-loc-rib-routes-top {
    container routes {
      dr:fieldnum 151;

      list route {
        dr:source "route";
        dr:fieldnum 151;
        dr:atomic-data;
        key "prefix origin path-id";

        uses rend-v6-loc-rib-keys;

        container state {
          dr:fieldnum 151;

          uses rend-v6-loc-rib-keys;
          uses rend-loc-rib-common-attr-refs;
          uses rend-bgp-common-route-annotations-state;
        }
        uses rend-bgp-unknown-attr-top;
      }
    }
  }

  grouping rend-adj-rib-keys {
    uses oc-bgprib:bgp-adj-rib-attr-state {
      augment "path-id" {
        dr:source "path-id";
        dr:fieldnum 52;
      }
    }
  }

  grouping rend-v4-adj-rib-keys {
    leaf "prefix" {
      type oc-inet:ipv4-prefix;
      dr:source "prefix";
      dr:fieldnum 51;
    }

    uses rend-adj-rib-keys;
  }

  grouping rend-v6-adj-rib-keys {
    leaf "prefix" {
      type oc-inet:ipv6-prefix;
      dr:source "prefix";
      dr:fieldnum 51;
    }

    uses rend-adj-rib-keys;
  }

  grouping rend-adj-rib-common-attr-refs {
    uses oc-bgprib:bgp-adj-rib-common-attr-refs {
      augment attr-index {
        dr:source "attr-index";
        dr:fieldnum 53;
      }

      augment community-index {
        dr:source "comm-index";
        dr:fieldnum 54;
      }

      augment ext-community-index {
        dr:source "ext-comm-index";
        dr:fieldnum 55;
      }
    }
  }

  grouping rend-v4-adj-rib-routes-top {
    container routes {
      dr:fieldnum 151;

      list route {
        dr:source "route";
        dr:fieldnum 151;
        dr:atomic-data;
        key "prefix path-id";

        uses rend-v4-adj-rib-keys;

        container state {
          dr:fieldnum 151;

          uses rend-v4-adj-rib-keys;
          uses rend-adj-rib-common-attr-refs;
          uses rend-bgp-common-route-annotations-state;
        }
        uses rend-bgp-unknown-attr-top;
      }
    }
  }

  grouping rend-v6-adj-rib-routes-top {
    container routes {
      dr:fieldnum 151;

      list route {
        dr:source "route";
        dr:fieldnum 151;
        dr:atomic-data;
        key "prefix path-id";

        uses rend-v6-adj-rib-keys;

        container state {
          dr:fieldnum 151;

          uses rend-v6-adj-rib-keys;
          uses rend-adj-rib-common-attr-refs;
          uses rend-bgp-common-route-annotations-state;
        }
        uses rend-bgp-unknown-attr-top;
      }
    }
  }

  grouping rend-adj-rib-in-post-route-annotations-state {
    uses oc-bgprib:bgp-adj-rib-in-post-route-annotations-state {
      augment best-path {
        dr:source "best-path";
        dr:fieldnum 60;
      }
    }
  }

  grouping rend-v4-adj-rib-in-post-routes-top {
    container routes {
      dr:fieldnum 151;

      list route {
        dr:source "route";
        dr:fieldnum 151;
        dr:atomic-data;
        key "prefix path-id";

        uses rend-v4-adj-rib-keys;

        container state {
          dr:fieldnum 151;

          uses rend-v4-adj-rib-keys;

          uses rend-adj-rib-common-attr-refs;
          uses rend-bgp-common-route-annotations-state;
          uses rend-adj-rib-in-post-route-annotations-state;
        }
        uses rend-bgp-unknown-attr-top;
      }
    }
  }

  grouping rend-v6-adj-rib-in-post-routes-top {
    container routes {
      dr:fieldnum 151;

      list route {
        dr:source "route";
        dr:fieldnum 151;
        dr:atomic-data;
        key "prefix path-id";

        uses rend-v6-adj-rib-keys;

        container state {
          dr:fieldnum 151;

          uses rend-v6-adj-rib-keys;

          uses rend-adj-rib-common-attr-refs;
          uses rend-bgp-common-route-annotations-state;
          uses rend-adj-rib-in-post-route-annotations-state;
        }
        uses rend-bgp-unknown-attr-top;
      }
    }
  }


  rpc juniper-netconf-get {
    dr:command-top-of-output "/oc-bgp-rib-information";
    dr:command-full-name "request drend juniper-netconf-get";
    dr:command-help "Default <get> rpc";

    output {
      container network-instances {
        list network-instance {
          key "name";
          dr:source "/rt-instances/rt-instance";
          dr:fieldnum 151;

          leaf name {
            type string;
            dr:source "instance_name";
            dr:fieldnum 51;
          }

          container protocols {
            dr:source "protocols";
            dr:fieldnum 151;

            list protocol {
              key "identifier name";
              dr:source "protocol";
              dr:fieldnum 151;

              leaf identifier {
                type string;
                dr:source identifier;
                dr:fieldnum 51;
              }

              leaf name {
                type string;
                dr:source protocol_instance_name;
                dr:fieldnum 52;
              }

              container bgp {
                dr:fieldnum 151;
                dr:source "bgp";

                container rib {
                  dr:source "rib";
                  dr:fieldnum 151;
                  dr:source-notification-name "bgp-rib-attr-set";
                  dr:source-notification-name "bgp-rib-comm";
                  dr:source-notification-name "bgp-rib-ext-comm";
                  uses rend-attr-sets-top;
                  uses rend-community-sets-top;
                  uses rend-ext-community-sets-top;
                  container afi-safis {
                    dr:fieldnum 154;

                    dr:source-notification-name "bgp-loc-rib-ipv4" ;
                    dr:source-notification-name "bgp-rib-in-pre-ipv4" ;
                    dr:source-notification-name "bgp-rib-in-post-ipv4" ;
                    dr:source-notification-name "bgp-rib-out-pre-ipv4" ;
                    dr:source-notification-name "bgp-rib-out-post-ipv4" ;
                    dr:source-notification-name "bgp-loc-rib-ipv6" ;
                    dr:source-notification-name "bgp-rib-in-pre-ipv6" ;
                    dr:source-notification-name "bgp-rib-in-post-ipv6" ;
                    dr:source-notification-name "bgp-rib-out-pre-ipv6" ;
                    dr:source-notification-name "bgp-rib-out-post-ipv6" ;
                    list afi-safi {
                      key "afi-safi-name";
                      dr:source "nlri";
                      dr:fieldnum 151;

                      uses rend-bgp-rib-state;

                      container state {
                        dr:fieldnum 151;

                        uses rend-bgp-rib-state;
                      }

                      container ipv4-unicast {
                        dr:source "ipv4-unicast";
                        dr:fieldnum 152;
                        dr:source-notification-name "bgp-loc-rib-ipv4" ;
                        dr:source-notification-name "bgp-rib-in-pre-ipv4" ;
                        dr:source-notification-name "bgp-rib-in-post-ipv4" ;
                        dr:source-notification-name "bgp-rib-out-pre-ipv4" ;
                        dr:source-notification-name "bgp-rib-out-post-ipv4" ;

                        container loc-rib {
                          dr:source "local-rib";
                          dr:fieldnum 151;
                          uses rend-v4-loc-rib-routes-top;
                        }

                        container neighbors {
                          dr:fieldnum 152;

                          list neighbor {
                            key "neighbor-address";
                            dr:source "neighbor";
                            dr:fieldnum 151;

                            leaf neighbor-address {
                              type string;
                              dr:source "neighbor-address";
                              dr:fieldnum 51;
                            }

                            container state {
                              dr:fieldnum 151;

                              leaf neighbor-address {
                                type string;
                                dr:source "neighbor-address";
                                dr:fieldnum 51;
                              }
                            }

                            container adj-rib-in-pre {
                              dr:source "adj-rib-in-pre";
                              dr:fieldnum 152;
                              uses rend-v4-adj-rib-routes-top;
                            }

                            container adj-rib-in-post {
                              dr:source "adj-rib-in-post";
                              dr:fieldnum 153;
                              uses rend-v4-adj-rib-in-post-routes-top;
                            }

                            container adj-rib-out-pre {
                              dr:source "adj-rib-out-pre";
                              dr:fieldnum 154;
                              uses rend-v4-adj-rib-routes-top;
                            }

                            container adj-rib-out-post {
                              dr:source "adj-rib-out-post";
                              dr:fieldnum 155;
                              uses rend-v4-adj-rib-routes-top;
                            }
                          }
                        }
                      }

                      container ipv6-unicast {
                        dr:source "ipv6-unicast";
                        dr:fieldnum 153;
                        dr:source-notification-name "bgp-loc-rib-ipv6" ;
                        dr:source-notification-name "bgp-rib-in-pre-ipv6" ;
                        dr:source-notification-name "bgp-rib-in-post-ipv6" ;
                        dr:source-notification-name "bgp-rib-out-pre-ipv6" ;
                        dr:source-notification-name "bgp-rib-out-post-ipv6" ;
                        container loc-rib {
                          dr:source "local-rib";
                          dr:fieldnum 151;
                          uses rend-v6-loc-rib-routes-top;
                        }

                        container neighbors {
                          dr:fieldnum 152;

                          list neighbor {
                            key neighbor-address;
                            dr:source "neighbor";
                            dr:fieldnum 151;

                            leaf neighbor-address {
                              type string;
                              dr:source "neighbor-address";
                              dr:fieldnum 51;
                            }

                            container state {
                              dr:fieldnum 151;

                              leaf neighbor-address {
                                type string;
                                dr:source "neighbor-address";
                                dr:fieldnum 51;
                              }
                            }

                            container adj-rib-in-pre {
                              dr:source "adj-rib-in-pre";
                              dr:fieldnum 152;
                              uses rend-v6-adj-rib-routes-top;
                            }

                            container adj-rib-in-post {
                              dr:source "adj-rib-in-post";
                              dr:fieldnum 153;
                              uses rend-v6-adj-rib-in-post-routes-top;
                            }

                            container adj-rib-out-pre {
                              dr:source "adj-rib-out-pre";
                              dr:fieldnum 154;
                              uses rend-v6-adj-rib-routes-top;
                            }

                            container adj-rib-out-post {
                              dr:source "adj-rib-out-post";
                              dr:fieldnum 155;
                              uses rend-v6-adj-rib-routes-top;
                            }
                          }
                        }
                      }
                    }
                  }
                }
              }
            }
          }
        }
      }
    }
  }


  grouping notif-v4-loc-rib {
    container protocols {
      dr:source "protocols";
      dr:fieldnum 151;

      list protocol {
        key "identifier name";
        dr:source "protocol";
        dr:fieldnum 151;

        leaf identifier {
          type string;
          dr:source identifier;
          dr:fieldnum 51;
        }

        leaf name {
          type string;
          dr:source protocol_instance_name;
          dr:fieldnum 52;
        }
        container bgp {
          dr:fieldnum 151;
          dr:source "bgp";
          container rib {
            dr:source "rib";
            dr:fieldnum 151;
            container afi-safis {
              list afi-safi {
                key "afi-safi-name";
                dr:source "nlri";
                dr:fieldnum 151;

                uses rend-bgp-rib-state;

                container state {
                  dr:fieldnum 151;

                  uses rend-bgp-rib-state;
                }
                container ipv4-unicast {
                  dr:source "ipv4-unicast";
                  dr:fieldnum 152;
                  container loc-rib {
                    dr:source "local-rib";
                    dr:fieldnum 151;
                    uses rend-v4-loc-rib-routes-top;
                  }
                }
              }
            }
          }
        }
      }
    }
  }

  grouping notif-v4-rib-in-pre {
    container protocols {
      dr:source "protocols";
      dr:fieldnum 151;

      list protocol {
        key "identifier name";
        dr:source "protocol";
        dr:fieldnum 151;

        leaf identifier {
          type string;
          dr:source identifier;
          dr:fieldnum 51;
        }

        leaf name {
          type string;
          dr:source protocol_instance_name;
          dr:fieldnum 52;
        }
        container bgp {
          dr:fieldnum 151;
          dr:source "bgp";
          container rib {
            dr:source "rib";
            dr:fieldnum 151;
            container afi-safis {
              list afi-safi {
                key "afi-safi-name";
                dr:source "nlri";
                dr:fieldnum 151;

                uses rend-bgp-rib-state;

                container state {
                  dr:fieldnum 151;

                  uses rend-bgp-rib-state;
                }
                container ipv4-unicast {
                  dr:source "ipv4-unicast";
                  dr:fieldnum 152;

                  container neighbors {
                    dr:fieldnum 152;

                    list neighbor {
                      key "neighbor-address";
                      dr:source "neighbor";
                      dr:fieldnum 151;

                      leaf neighbor-address {
                        type string;
                        dr:source "neighbor-address";
                        dr:fieldnum 51;
                      }

                      container state {
                        dr:fieldnum 151;

                        leaf neighbor-address {
                          type string;
                          dr:source "neighbor-address";
                          dr:fieldnum 51;
                        }
                      }

                      container adj-rib-in-pre {
                        dr:source "adj-rib-in-pre";
                        dr:fieldnum 152;
                        uses rend-v4-adj-rib-routes-top;
                      }
                    }
                  }
                }
              }
            }
          }
        }
      }
    }
  }

  grouping notif-v4-rib-in-post {
    container protocols {
      dr:source "protocols";
      dr:fieldnum 151;

      list protocol {
        key "identifier name";
        dr:source "protocol";
        dr:fieldnum 151;

        leaf identifier {
          type string;
          dr:source identifier;
          dr:fieldnum 51;
        }

        leaf name {
          type string;
          dr:source protocol_instance_name;
          dr:fieldnum 52;
        }
        container bgp {
          dr:fieldnum 151;
          dr:source "bgp";
          container rib {
            dr:source "rib";
            dr:fieldnum 151;
            container afi-safis {
              list afi-safi {
                key "afi-safi-name";
                dr:source "nlri";
                dr:fieldnum 151;

                uses rend-bgp-rib-state;

                container state {
                  dr:fieldnum 151;

                  uses rend-bgp-rib-state;
                }
                container ipv4-unicast {
                  dr:source "ipv4-unicast";
                  dr:fieldnum 152;

                  container neighbors {
                    dr:fieldnum 152;

                    list neighbor {
                      key "neighbor-address";
                      dr:source "neighbor";
                      dr:fieldnum 151;

                      leaf neighbor-address {
                        type string;
                        dr:source "neighbor-address";
                        dr:fieldnum 51;
                      }

                      container state {
                        dr:fieldnum 151;

                        leaf neighbor-address {
                          type string;
                          dr:source "neighbor-address";
                          dr:fieldnum 51;
                        }
                      }

                      container adj-rib-in-post {
                        dr:source "adj-rib-in-post";
                        dr:fieldnum 153;
                        uses rend-v4-adj-rib-routes-top;
                      }
                    }
                  }
                }
              }
            }
          }
        }
      }
    }
  }


  grouping notif-v4-rib-out-pre {
    container protocols {
      dr:source "protocols";
      dr:fieldnum 151;

      list protocol {
        key "identifier name";
        dr:source "protocol";
        dr:fieldnum 151;

        leaf identifier {
          type string;
          dr:source identifier;
          dr:fieldnum 51;
        }

        leaf name {
          type string;
          dr:source protocol_instance_name;
          dr:fieldnum 52;
        }
        container bgp {
          dr:fieldnum 151;
          dr:source "bgp";
          container rib {
            dr:source "rib";
            dr:fieldnum 151;
            container afi-safis {
              list afi-safi {
                key "afi-safi-name";
                dr:source "nlri";
                dr:fieldnum 151;

                uses rend-bgp-rib-state;

                container state {
                  dr:fieldnum 151;

                  uses rend-bgp-rib-state;
                }
                container ipv4-unicast {
                  dr:source "ipv4-unicast";
                  dr:fieldnum 152;

                  container neighbors {
                    dr:fieldnum 152;

                    list neighbor {
                      key "neighbor-address";
                      dr:source "neighbor";
                      dr:fieldnum 151;

                      leaf neighbor-address {
                        type string;
                        dr:source "neighbor-address";
                        dr:fieldnum 51;
                      }

                      container state {
                        dr:fieldnum 151;

                        leaf neighbor-address {
                          type string;
                          dr:source "neighbor-address";
                          dr:fieldnum 51;
                        }
                      }

                      container adj-rib-out-pre {
                        dr:source "adj-rib-out-pre";
                        dr:fieldnum 154;
                        uses rend-v4-adj-rib-routes-top;
                      }
                    }
                  }
                }
              }
            }
          }
        }
      }
    }
  }

  grouping notif-v4-rib-out-post {
    container protocols {
      dr:source "protocols";
      dr:fieldnum 151;

      list protocol {
        key "identifier name";
        dr:source "protocol";
        dr:fieldnum 151;

        leaf identifier {
          type string;
          dr:source identifier;
          dr:fieldnum 51;
        }

        leaf name {
          type string;
          dr:source protocol_instance_name;
          dr:fieldnum 52;
        }
        container bgp {
          dr:fieldnum 151;
          dr:source "bgp";
          container rib {
            dr:source "rib";
            dr:fieldnum 151;
            container afi-safis {
              list afi-safi {
                key "afi-safi-name";
                dr:source "nlri";
                dr:fieldnum 151;

                uses rend-bgp-rib-state;

                container state {
                  dr:fieldnum 151;

                  uses rend-bgp-rib-state;
                }
                container ipv4-unicast {
                  dr:source "ipv4-unicast";
                  dr:fieldnum 152;

                  container neighbors {
                    dr:fieldnum 152;

                    list neighbor {
                      key "neighbor-address";
                      dr:source "neighbor";
                      dr:fieldnum 151;

                      leaf neighbor-address {
                        type string;
                        dr:source "neighbor-address";
                        dr:fieldnum 51;
                      }

                      container state {
                        dr:fieldnum 151;

                        leaf neighbor-address {
                          type string;
                          dr:source "neighbor-address";
                          dr:fieldnum 51;
                        }
                      }

                      container adj-rib-out-post {
                        dr:source "adj-rib-out-post";
                        dr:fieldnum 155;
                        uses rend-v4-adj-rib-routes-top;
                      }
                    }
                  }
                }
              }
            }
          }
        }
      }
    }
  }

  grouping notif-v6-loc-rib {
    container protocols {
      dr:source "protocols";
      dr:fieldnum 151;

      list protocol {
        key "identifier name";
        dr:source "protocol";
        dr:fieldnum 151;

        leaf identifier {
          type string;
          dr:source identifier;
          dr:fieldnum 51;
        }

        leaf name {
          type string;
          dr:source protocol_instance_name;
          dr:fieldnum 52;
        }
        container bgp {
          dr:fieldnum 151;
          dr:source "bgp";
          container rib {
            dr:source "rib";
            dr:fieldnum 151;
            container afi-safis {
              list afi-safi {
                key "afi-safi-name";
                dr:source "nlri";
                dr:fieldnum 151;

                uses rend-bgp-rib-state;

                container state {
                  dr:fieldnum 151;

                  uses rend-bgp-rib-state;
                }
                container ipv6-unicast {
                  dr:source "ipv6-unicast";
                  dr:fieldnum 153;
                  container loc-rib {
                    dr:source "local-rib";
                    dr:fieldnum 151;
                    uses rend-v6-loc-rib-routes-top;
                  }
                }
              }
            }
          }
        }
      }
    }
  }

  grouping notif-v6-rib-in-pre {
    container protocols {
      dr:source "protocols";
      dr:fieldnum 151;

      list protocol {
        key "identifier name";
        dr:source "protocol";
        dr:fieldnum 151;

        leaf identifier {
          type string;
          dr:source identifier;
          dr:fieldnum 51;
        }

        leaf name {
          type string;
          dr:source protocol_instance_name;
          dr:fieldnum 52;
        }
        container bgp {
          dr:fieldnum 151;
          dr:source "bgp";
          container rib {
            dr:source "rib";
            dr:fieldnum 151;
            container afi-safis {
              list afi-safi {
                key "afi-safi-name";
                dr:source "nlri";
                dr:fieldnum 151;

                uses rend-bgp-rib-state;

                container state {
                  dr:fieldnum 151;

                  uses rend-bgp-rib-state;
                }
                container ipv6-unicast {
                  dr:source "ipv6-unicast";
                  dr:fieldnum 153;

                  container neighbors {
                    dr:fieldnum 152;

                    list neighbor {
                      key "neighbor-address";
                      dr:source "neighbor";
                      dr:fieldnum 151;

                      leaf neighbor-address {
                        type string;
                        dr:source "neighbor-address";
                        dr:fieldnum 51;
                      }

                      container state {
                        dr:fieldnum 151;

                        leaf neighbor-address {
                          type string;
                          dr:source "neighbor-address";
                          dr:fieldnum 51;
                        }
                      }

                      container adj-rib-in-pre {
                        dr:source "adj-rib-in-pre";
                        dr:fieldnum 152;
                        uses rend-v6-adj-rib-routes-top;
                      }
                    }
                  }
                }
              }
            }
          }
        }
      }
    }
  }

  grouping notif-v6-rib-in-post {
    container protocols {
      dr:source "protocols";
      dr:fieldnum 151;

      list protocol {
        key "identifier name";
        dr:source "protocol";
        dr:fieldnum 151;

        leaf identifier {
          type string;
          dr:source identifier;
          dr:fieldnum 51;
        }

        leaf name {
          type string;
          dr:source protocol_instance_name;
          dr:fieldnum 52;
        }
        container bgp {
          dr:fieldnum 151;
          dr:source "bgp";
          container rib {
            dr:source "rib";
            dr:fieldnum 151;
            container afi-safis {
              list afi-safi {
                key "afi-safi-name";
                dr:source "nlri";
                dr:fieldnum 151;

                uses rend-bgp-rib-state;

                container state {
                  dr:fieldnum 151;

                  uses rend-bgp-rib-state;
                }
                container ipv6-unicast {
                  dr:source "ipv6-unicast";
                  dr:fieldnum 153;

                  container neighbors {
                    dr:fieldnum 152;

                    list neighbor {
                      key "neighbor-address";
                      dr:source "neighbor";
                      dr:fieldnum 151;

                      leaf neighbor-address {
                        type string;
                        dr:source "neighbor-address";
                        dr:fieldnum 51;
                      }

                      container state {
                        dr:fieldnum 151;

                        leaf neighbor-address {
                          type string;
                          dr:source "neighbor-address";
                          dr:fieldnum 51;
                        }
                      }

                      container adj-rib-in-post {
                        dr:source "adj-rib-in-post";
                        dr:fieldnum 153;
                        uses rend-v6-adj-rib-routes-top;
                      }
                    }
                  }
                }
              }
            }
          }
        }
      }
    }
  }

  grouping notif-v6-rib-out-pre {
    container protocols {
      dr:source "protocols";
      dr:fieldnum 151;

      list protocol {
        key "identifier name";
        dr:source "protocol";
        dr:fieldnum 151;

        leaf identifier {
          type string;
          dr:source identifier;
          dr:fieldnum 51;
        }

        leaf name {
          type string;
          dr:source protocol_instance_name;
          dr:fieldnum 52;
        }
        container bgp {
          dr:fieldnum 151;
          dr:source "bgp";
          container rib {
            dr:source "rib";
            dr:fieldnum 151;
            container afi-safis {
              list afi-safi {
                key "afi-safi-name";
                dr:source "nlri";
                dr:fieldnum 151;

                uses rend-bgp-rib-state;

                container state {
                  dr:fieldnum 151;

                  uses rend-bgp-rib-state;
                }
                container ipv6-unicast {
                  dr:source "ipv6-unicast";
                  dr:fieldnum 153;

                  container neighbors {
                    dr:fieldnum 152;

                    list neighbor {
                      key "neighbor-address";
                      dr:source "neighbor";
                      dr:fieldnum 151;

                      leaf neighbor-address {
                        type string;
                        dr:source "neighbor-address";
                        dr:fieldnum 51;
                      }

                      container state {
                        dr:fieldnum 151;

                        leaf neighbor-address {
                          type string;
                          dr:source "neighbor-address";
                          dr:fieldnum 51;
                        }
                      }

                      container adj-rib-out-pre {
                        dr:source "adj-rib-out-pre";
                        dr:fieldnum 154;
                        uses rend-v6-adj-rib-routes-top;
                      }
                    }
                  }
                }
              }
            }
          }
        }
      }
    }
  }

  grouping notif-v6-rib-out-post {
    container protocols {
      dr:source "protocols";
      dr:fieldnum 151;

      list protocol {
        key "identifier name";
        dr:source "protocol";
        dr:fieldnum 151;

        leaf identifier {
          type string;
          dr:source identifier;
          dr:fieldnum 51;
        }

        leaf name {
          type string;
          dr:source protocol_instance_name;
          dr:fieldnum 52;
        }
        container bgp {
          dr:fieldnum 151;
          dr:source "bgp";
          container rib {
            dr:source "rib";
            dr:fieldnum 151;
            container afi-safis {
              list afi-safi {
                key "afi-safi-name";
                dr:source "nlri";
                dr:fieldnum 151;

                uses rend-bgp-rib-state;

                container state {
                  dr:fieldnum 151;

                  uses rend-bgp-rib-state;
                }
                container ipv6-unicast {
                  dr:source "ipv6-unicast";
                  dr:fieldnum 153;

                  container neighbors {
                    dr:fieldnum 152;

                    list neighbor {
                      key "neighbor-address";
                      dr:source "neighbor";
                      dr:fieldnum 151;

                      leaf neighbor-address {
                        type string;
                        dr:source "neighbor-address";
                        dr:fieldnum 51;
                      }

                      container state {
                        dr:fieldnum 151;

                        leaf neighbor-address {
                          type string;
                          dr:source "neighbor-address";
                          dr:fieldnum 51;
                        }
                      }

                      container adj-rib-out-post {
                        dr:source "adj-rib-out-post";
                        dr:fieldnum 155;
                        uses rend-v6-adj-rib-routes-top;
                      }
                    }
                  }
                }
              }
            }
          }
        }
      }
    }
  }

  notification bgp-loc-rib-ipv4 {
    dr:source-notification-name "bgp-loc-rib-ipv4";
    container network-instances {
      list network-instance {
        key "name";
        dr:source "/notification/bgp-loc-rib-ipv4/network-instances/network-instance/";
        dr:fieldnum 151;

        leaf name {
          type string;
          dr:source "instance_name";
          dr:fieldnum 51;
        }
        uses notif-v4-loc-rib;
      }
    }
  }

  notification bgp-rib-in-pre-ipv4 {
    dr:source-notification-name "bgp-rib-in-pre-ipv4";
    container network-instances {
      list network-instance {
        key "name";
        dr:source "/notification/bgp-rib-in-pre-ipv4/rib/";
        dr:fieldnum 151;

        leaf name {
          type string;
          dr:source "instance_name";
          dr:fieldnum 51;
        }
        uses notif-v4-rib-in-pre;
      }
    }
  }

  notification bgp-rib-in-post-ipv4 {
    dr:source-notification-name "bgp-rib-in-post-ipv4";
    container network-instances {
      list network-instance {
        key "name";
        dr:source "/notification/bgp-rib-in-post-ipv4/rib/";
        dr:fieldnum 151;

        leaf name {
          type string;
          dr:source "instance_name";
          dr:fieldnum 51;
        }
        uses notif-v4-rib-in-post;
      }
    }
  }

  notification bgp-rib-out-pre-ipv4 {
    dr:source-notification-name "bgp-rib-out-pre-ipv4";
    container network-instances {
      list network-instance {
        key "name";
        dr:source "/notification/bgp-rib-out-pre-ipv4/rib/";
        dr:fieldnum 151;

        leaf name {
          type string;
          dr:source "instance_name";
          dr:fieldnum 51;
        }
        uses notif-v4-rib-out-pre;
      }
    }
  }

  notification bgp-rib-out-post-ipv4 {
    dr:source-notification-name "bgp-rib-out-post-ipv4";
    container network-instances {
      list network-instance {
        key "name";
        dr:source "/notification/bgp-rib-out-post-ipv4/rib/";
        dr:fieldnum 151;

        leaf name {
          type string;
          dr:source "instance_name";
          dr:fieldnum 51;
        }
        uses notif-v4-rib-out-post;
      }
    }
  }

  notification bgp-loc-rib-ipv6 {
    dr:source-notification-name "bgp-loc-rib-ipv6";
    container network-instances {
      list network-instance {
        key "name";
        dr:source "/notification/bgp-loc-rib-ipv6/rib/";
        dr:fieldnum 151;

        leaf name {
          type string;
          dr:source "instance_name";
          dr:fieldnum 51;
        }
        uses notif-v6-loc-rib;
      }
    }
  }

  notification bgp-rib-in-pre-ipv6 {
    dr:source-notification-name "bgp-rib-in-pre-ipv6";
    container network-instances {
      list network-instance {
        key "name";
        dr:source "/notification/bgp-rib-in-pre-ipv6/rib/";
        dr:fieldnum 151;

        leaf name {
          type string;
          dr:source "instance_name";
          dr:fieldnum 51;
        }
        uses notif-v6-rib-in-pre;
      }
    }
  }

  notification bgp-rib-in-post-ipv6 {
    dr:source-notification-name "bgp-rib-in-post-ipv6";
    container network-instances {
      list network-instance {
        key "name";
        dr:source "/notification/bgp-rib-in-post-ipv6/rib/";
        dr:fieldnum 151;

        leaf name {
          type string;
          dr:source "instance_name";
          dr:fieldnum 51;
        }
        uses notif-v6-rib-in-post;
      }
    }
  }

  notification bgp-rib-out-pre-ipv6 {
    dr:source-notification-name "bgp-rib-out-pre-ipv6";
    container network-instances {
      list network-instance {
        key "name";
        dr:source "/notification/bgp-rib-out-pre-ipv6/rib/";
        dr:fieldnum 151;

        leaf name {
          type string;
          dr:source "instance_name";
          dr:fieldnum 51;
        }
        uses notif-v6-rib-out-pre;
      }
    }
  }

  notification bgp-rib-out-post-ipv6 {
    dr:source-notification-name "bgp-rib-out-post-ipv6";
    container network-instances {
      list network-instance {
        key "name";
        dr:source "/notification/bgp-rib-out-post-ipv6/rib/";
        dr:fieldnum 151;

        leaf name {
          type string;
          dr:source "instance_name";
          dr:fieldnum 51;
        }
        uses notif-v6-rib-out-post;
      }
    }
  }

  notification oc-bgp-rib-comm {
    dr:source-notification-name "bgp-rib-comm";
    container network-instances {
      dr:source "/notification/bgp-rib-comm/network-instances";
      dr:fieldnum 151;
      list network-instance {
        key "name";
        dr:source "network-instance";
        dr:fieldnum 151;

        leaf name {
          type string;
          dr:source "instance_name";
          dr:fieldnum 51;
        }
        container protocols {
          dr:source "protocols";
          dr:fieldnum 151;

          list protocol {
            key "identifier name";
            dr:source "protocol";
            dr:fieldnum 151;

            leaf identifier {
              type string;
              dr:source identifier;
              dr:fieldnum 51;
            }

            leaf name {
              type string;
              dr:source protocol_instance_name;
              dr:fieldnum 52;
            }
            container bgp {
              dr:fieldnum 151;
              dr:source "bgp";
              container rib {
                dr:source "rib";
                dr:fieldnum 151;
                container communities {
                  dr:source "communities";
                  dr:fieldnum 152;
                  list community {
                    key "index";
                    dr:source "community-list";
                    dr:fieldnum 151;

                    leaf index {
                      type uint64;
                      dr:source comm-index;
                      dr:fieldnum 51;
                    }
                    container state {
                      dr:source "state";
                      dr:fieldnum 151;
                      leaf index {
                        dr:source "comm-index";
                        type uint64;
                        dr:fieldnum 51;
                      }
                      leaf-list community {
                        dr:source "community";
                        type string;
                        dr:fieldnum 52;
                      }
                    }
                  }
                }
              }
            }
          }
        }
      }
    }
  }

  notification oc-bgp-rib-ext-comm {
    dr:source-notification-name "bgp-rib-ext-comm";
    container network-instances {
      dr:source "/notification/bgp-rib-ext-comm/network-instances";
      dr:fieldnum 151;
      list network-instance {
        key "name";
        dr:source "network-instance";
        dr:fieldnum 151;

        leaf name {
          type string;
          dr:source "instance_name";
          dr:fieldnum 51;
        }
        container protocols {
          dr:source "protocols";
          dr:fieldnum 151;

          list protocol {
            key "identifier name";
            dr:source "protocol";
            dr:fieldnum 151;

            leaf identifier {
              type string;
              dr:source identifier;
              dr:fieldnum 51;
            }

            leaf name {
              type string;
              dr:source protocol_instance_name;
              dr:fieldnum 52;
            }
            container bgp {
              dr:fieldnum 151;
              dr:source "bgp";
              container rib {
                dr:source "rib";
                dr:fieldnum 151;
                container ext-communities {
                  dr:source "ext-communities";
                  dr:fieldnum 153;
                  list ext-community {
                    key "index";
                    dr:source "ext-community-list";
                    dr:fieldnum 151;

                    leaf index {
                      type uint64;
                      dr:source comm-index;
                      dr:fieldnum 51;
                    }
                    container state {
                      dr:source "state";
                      dr:fieldnum 151;
                      leaf index {
                        dr:source "comm-index";
                        type uint64;
                        dr:fieldnum 51;
                      }
                      leaf-list ext-community {
                        dr:source "ext-community";
                        type string;
                        dr:fieldnum 52;
                      }
                    }
                  }
                }
              }
            }
          }
        }
      }
    }
  }

 notification oc-bgp-rib-attr-set {
    dr:source-notification-name "bgp-rib-attr-set";
    container network-instances {
      dr:source "/notification/bgp-rib-attr-set/network-instances";
      dr:fieldnum 151;
      list network-instance {
        key "name";
        dr:source "network-instance";
        dr:fieldnum 151;

        leaf name {
          type string;
          dr:source "instance_name";
          dr:fieldnum 51;
        }
        container protocols {
          dr:source "protocols";
          dr:fieldnum 151;

          list protocol {
            key "identifier name";
            dr:source "protocol";
            dr:fieldnum 151;

            leaf identifier {
              type string;
              dr:source identifier;
              dr:fieldnum 51;
            }

            leaf name {
              type string;
              dr:source protocol_instance_name;
              dr:fieldnum 52;
            }
            container bgp {
              dr:fieldnum 151;
              dr:source "bgp";
              container rib {
                dr:source "rib";
                dr:fieldnum 151;
                container attr-sets {
                  dr:source "attr-sets";
                  dr:fieldnum 151;
                  list attr-set {
                    key "index";
                    dr:source "attr-set";
                    dr:fieldnum 151;

                    leaf index {
                      type uint64;
                      dr:source attr-index;
                      dr:fieldnum 51;
                    }
                    container state {
                      dr:source "state";
                      dr:fieldnum 151;
                      leaf index {
                        dr:source "attr-index";
                        type uint64;
                        dr:fieldnum 51;
                      }
                      leaf origin {
                        dr:source "origin";
                        type string;
                        dr:fieldnum 52;
                        dr:map IGP { dr:map-from 0; }
                        dr:map EGP { dr:map-from 1; }
                        dr:map INCOMPLETE { dr:map-from 2; }
                      }
                      leaf atomic-aggregate {
                        dr:source "atomic-aggregate";
                        type boolean;
                        dr:fieldnum 53;
                      }
                      leaf next-hop {
                        dr:source "next-hop";
                        type oc-inet:ip-address;
                        dr:fieldnum 54;
                      }
                      leaf med {
                        dr:source "med";
                        type uint32;
                        dr:fieldnum 55;
                      }
                      leaf local-pref {
                        dr:source "local-pref";
                        type uint32;
                        dr:fieldnum 56;
                      }
                      leaf originator-id {
                        dr:source "originator-id";
                        type oc-inet:ipv4-address;
                        dr:fieldnum 57;
                      }
                      leaf-list cluster-list {
                        dr:source "cluster-list";
                        type string;
                        dr:fieldnum 58;
                      }
                      leaf aigp {
                        dr:source "aigp";
                        type uint64;
                        dr:fieldnum 59;
                      }
                    }
                    container aggregator {
                      dr:source "aggregator";
                      dr:fieldnum 152;
                      container state {
                        dr:source "state";
                        dr:fieldnum 151;
                        leaf as {
                          dr:source "as";
                          type uint32;
                          dr:fieldnum 51;
                        }
                        leaf as4 {
                          dr:source "as4";
                          type uint32;
                          dr:fieldnum 52;
                        }
                        leaf address {
                          dr:source "address";
                          type oc-inet:ipv4-address;
                          dr:fieldnum 53;
                        }
                      }
                    }
                    container as-path {
                      dr:source "as-path";
                      dr:fieldnum 153;
                      list as-segment {
                        dr:source "as-segment";
                        dr:fieldnum 151;
                        container state {
                          dr:source "state";
                          dr:fieldnum 151;
                          leaf type {
                            dr:source "type";
                            type string;
                            dr:fieldnum 51;
                            dr:map AS_SEQ { dr:map-from 2; }
                            dr:map AS_SET { dr:map-from 1; }
                            dr:map AS_CONFED_SEQUENCE { dr:map-from 3; }
                            dr:map AS_CONFED_SET { dr:map-from 4; }
                          }
                          leaf-list member {
                            dr:source "member";
                            type string;
                            dr:fieldnum 52;
                          }
                        }
                      }
                    }
                    container as4-path {
                      dr:source "as4-path";
                      dr:fieldnum 154;
                      list as4-segment {
                        dr:source "as4-segment";
                        dr:fieldnum 151;
                          container state {
                          dr:source "state";
                          dr:fieldnum 151;
                          leaf type {
                            dr:source "type";
                            type string;
                            dr:fieldnum 51;
                            dr:map AS_SEQ { dr:map-from 2; }
                            dr:map AS_SET { dr:map-from 1; }
                            dr:map AS_CONFED_SEQUENCE { dr:map-from 3; }
                            dr:map AS_CONFED_SET { dr:map-from 4; }
                          }
                          leaf-list member {
                            dr:source "member";
                            type string;
                            dr:fieldnum 52;
                          }
                        }
                      }
                    }
                  }
                }
              }
            }
          }
        }
      }
    }
  }

}
