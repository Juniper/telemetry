module junos-jl2tpd-annotations {
    yang-version 1;
    namespace "http://juniper.net/yang/junos/jl2tpd/annotations";
    prefix "junos-jl2tpd-ann";
    import junos-jl2tpd { prefix junos-jl2tpd; }
    import junos-extension { prefix junos; }
    organization "Juniper Network Inc.";
    revision "2022-09-22" {
        description "Initial version to add native jl2tpd model product support information";
    }
    augment "/junos-jl2tpd:junos/junos-jl2tpd:system/junos-jl2tpd:subscriber-management/" +
            "junos-jl2tpd:client-protocols/junos-jl2tpd:l2tp" {
        junos:product "mx304 mx10001 mx10002 mx960 mx480 mx240 mx5-t mx10-t mx40-t mx80 mx80-t mx80-48t mx80-p mx104 mxtsr80 mx2020 mx2010 mx2008 vmx vrr";
        junos:product "ex9204 ex9208 ex9214 ex9251 ex9253";
        junos:product "ACX7100-48L ACX7100-32C";
        junos:product "cbng";
    }
}
