module junos-state-anomalies-fib-annotations {
    yang-version 1;
    namespace "http://juniper.net/junos/state/anomalies/fib/annotations";
    prefix "js-anom-fib-ann";
    import junos-state { prefix js; }
    import junos-state-system { prefix js-sys; }
    import junos-state-anomalies { prefix js-anom; }
    import junos-state-anomalies-fib { prefix js-anom-fib; }
    import junos-extension { prefix junos; }
    organization "Juniper Network Inc.";
    revision "2023-02-14" {
        description "Initial version to add junos state fib anomalies model product support information";
    }
    augment "/js:state/js-sys:system/js-anom:anomalies/js-anom-fib:fib" {
        junos:product "ptx10001-36mr ptx10003-160c ptx10003-80c ptx10003-81cd ptx10004 ptx10008 ptx10016";
        junos:product "mx2020 mx960 mx240";
        junos:product "ptx5000 ptx1000";
        junos:product "acx7509 ACX7024";
    }
}
