module junos-openconfig-if-ip-annotations {
    yang-version "1";
    namespace "http://yang.juniper.net/openconfig/if/ip/annotations";
    prefix "jnx-oc-ip-ann";
    import openconfig-if-ip { prefix oc-ip; }
    import openconfig-inet-types { prefix oc-inet; }
    import openconfig-interfaces { prefix oc-if; }
    import openconfig-vlan { prefix oc-vlan; }
    import openconfig-yang-types { prefix oc-yang; }
    import openconfig-extensions { prefix oc-ext; }
    import junos-extension { prefix junos; }
    organization "Juniper Networks";
    description
       "This module contains JUNOS annotations for openConfig-if-ip product model";
    revision "2022-04-27" {
        description "Initial revision";
    }
    augment "/oc-if:interfaces/oc-if:interface/oc-if:subinterfaces/oc-if:subinterface" +
            "/oc-ip:ipv4/oc-ip:state/oc-ip:counters" {
        junos:product "mx304 mx10001 mx10002 mx960 mx480 mx240 mx5-t mx10-t mx40-t mx80 mx80-t mx80-48t mx80-p mx104 mxtsr80 mx2020 mx2010 mx2008 vmx vrr";
        junos:product-exclude "mx5-t mx10-t mx40-t mx80 mx80-t mx80-48t mx80-p mx104 mxtsr80";
        junos:product "ptx10001-36mr ptx10001-27cd ptx10016 ptx10008 ptx10004";
        junos:product-tvp "ex2300-24p ex2300-48p ex2300-24mp ex2300-48mp";
        junos:product-tvp "ex2300-24t ex2300-48p ex2300-48t ex2300c-12t ex2300c-12p ex2300-24t-dc";
        junos:product-tvp "ex3400-24p ex3400-24t ex3400-48p ex3400-48t";
        junos:product-tvp "ex4100-f-12t ex4100-f-12p";
        junos:product-tvp "ex4100-24t ex4100-f-24t ex4100-24p ex4100-f-24p ex4100-24mp";
        junos:product-tvp "ex4100-48t ex4100-48p ex4100-48mp ex4100-f-48t ex4100-f-48p";
        junos:product-tvp "ex4300-48mp";
        junos:product-tvp "ex4400-24x ex4400-24mp ex4400-24p ex4400-24t";
        junos:product-tvp "ex4400-48f ex4400-48mp ex4400-48p ex4400-48t";
        junos:product-tvp "qfx5120-48ym qfx5120-48t qfx5210-64c qfx5120-48y-8c ex4650-48y-8c qfx5120-32c";
        junos:product-tvp "qfx5110-24q-2p qfx5110-32q qfx5110-48s-4c qfx5110-48s-4q qfx5110-48t-6q";
        junos:product-tvp "qfx5200-48y qfx5200-32c";
    }
    augment "/oc-if:interfaces/oc-if:interface/oc-if:subinterfaces/oc-if:subinterface" +
            "/oc-ip:ipv6/oc-ip:state/oc-ip:counters" {
        junos:product "mx304 mx10001 mx10002 mx960 mx480 mx240 mx5-t mx10-t mx40-t mx80 mx80-t mx80-48t mx80-p mx104 mxtsr80 mx2020 mx2010 mx2008 vmx vrr";
        junos:product-exclude "mx5-t mx10-t mx40-t mx80 mx80-t mx80-48t mx80-p mx104 mxtsr80";
        junos:product "ptx10001-36mr ptx10001-27cd ptx10003-160c ptx10003-80c ptx10016 ptx10008 ptx10004";
    }
}
