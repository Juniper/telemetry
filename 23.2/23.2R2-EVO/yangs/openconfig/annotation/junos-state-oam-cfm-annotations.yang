module junos-state-oam-cfm-annotations {
  yang-version 1;
  namespace "http://yang.juniper.net/junos/state/oam/cfm/annotations";
  prefix "js-oam-cfm-ann";
  import junos-state { prefix js; }
  import junos-state-protocols { prefix js-pro; }
  import junos-state-oam { prefix js-oam; }
  import junos-state-oam-cfm { prefix js-oam-cfm; }
  import junos-extension { prefix junos; }
  organization "Juniper Network Inc.";
  revision "2023-01-13" {
    description "Initial version to add connectivity fault management model product support information";
  }
  augment "/js:state/js-pro:protocols/js-oam:oam/js-oam:ethernet/js-oam-cfm:connectivity-fault-management" {
    junos:product "mx304 mx10001 mx10002 mx960 mx480 mx240 mx5-t mx10-t mx40-t mx80 mx80-t mx80-48t mx80-p mx104 mxtsr80 mx2020 mx2010 mx2008 vmx vrr";
    junos:product-exclude "mx5-t mx10-t mx40-t mx80 mx80-t mx80-48t mx80-p mx104 mxtsr80";
    junos:product "acx7509 ACX7024 ACX7100-48L ACX7100-32C acx7908";
  }
}
