module junos-openconfig-platform-annotations {
    yang-version "1";
    namespace "http://yang.juniper.net/openconfig/platform/annotations";
    prefix "jnx-oc-platform-ann";
    import openconfig-platform-linecard { prefix oc-linecard; }
    import openconfig-platform { prefix oc-platform; }
    import jnx-aug-openconfig-platform { prefix jnx-oc-platform; }
    import junos-extension { prefix junos; }
    organization "Juniper Networks";
    description
       "This module contains JUNOS augments to OpenConfig components product model";
    revision "2022-01-13" {
        description "Initial revision";
    }
    augment "/oc-platform:components" {
        junos:product "ptx1000 ptx5000 ptx21000 ptx10003-160c ptx10003-80c qfx10003-160c qfx10003-80c ptx10003-81cd ptx10001-36mr ptx10001-27cd ptx10016 ptx10008 ptx10004 qfx5220-32cd qfx5220-128c qfx5130-32cd qfx5009 qfx5700 qfx5230-64cd qfx5130-48c qfx5130-48cm acx753 r6273 ACX7100-48L ACX7100-32C acx7509 wbonl acx7908 ACX7024 acx7332 acx7348 QFX7100-48L ptx10002-36qdd";
        junos:product "mx304 mx10001 mx10002 mx960 mx480 mx240 mx5-t mx10-t mx40-t mx80 mx80-t mx80-48t mx80-p mx104 mxtsr80 mx2020 mx2010 mx2008 vmx vrr";
        junos:product "ex9204 ex9208 ex9214 ex9251 ex9253";
        junos:product-exclude "mx5-t mx10-t mx40-t mx80 mx80-t mx80-48t mx80-p mx104 mxtsr80";
        junos:product "ptx5000 ptx9000 ptx3000 sng_olive ptx1000 ptx21000 qfx10002-60c ptx10003-160c ptx10003-80c qfx10003-160c qfx10003-80c ptx10003-81cd ptx10001-36mr ptx10001-27cd ptx10002-36qdd ptx10016 ptx10008 ptx10004 qfx10016 qfx10008";
        junos:product "srx5400 srx5600 srx5800 vsrx";
        junos:product-tvp "mx10004 mx10008 mx10016";
        junos:product-tvp "srx1500 srx4100 srx4200 srx4600 srx4800";
        junos:product-tvp "ex2300-24p ex2300-48p ex2300-24mp ex2300-48mp";
        junos:product-tvp "ex2300-24t ex2300-48p ex2300-48t ex2300c-12t ex2300c-12p ex2300-24t-dc";
        junos:product-tvp "ex3400-24p ex3400-24t ex3400-48p ex3400-48t";
        junos:product-tvp "ex4100-f-12t ex4100-f-12p";
        junos:product-tvp "ex4100-24t ex4100-f-24t ex4100-24p ex4100-f-24p ex4100-24mp";
        junos:product-tvp "ex4100-48t ex4100-48p ex4100-48mp ex4100-f-48t ex4100-f-48p";
        junos:product-tvp "ex4300-48mp";
        junos:product-tvp "ex4400-24x ex4400-24mp ex4400-24p ex4400-24t";
        junos:product-tvp "ex4400-48f ex4400-48mp ex4400-48p ex4400-48t";
        junos:product-tvp "qfx5120-48ym qfx5120-48t qfx5210-64c qfx5120-48y-8c ex4650-48y-8c qfx5120-32c";
        junos:product-tvp "qfx5110-24q-2p qfx5110-32q qfx5110-48s-4c qfx5110-48s-4q qfx5110-48t-6q";
        junos:product-tvp "qfx5200-48y qfx5200-32c";
    }
    augment "/oc-platform:components/oc-platform:component/" +
        "oc-platform:state" {
        junos:product "mx304 mx960 mx2010 mx2020";
        junos:product-tvp "mx10004 mx10008 mx10016";
        junos:product "ptx10003-160c ptx10003-80c qfx10003-160c qfx10003-80c ptx10016 ptx10008 ptx10004 ptx10001-36mr ptx10001-27cd ptx10002-36qdd";
        junos:product "acx7908 acx7509 ACX7100-48L ACX7100-32C";
        junos:product-tvp "ex2300-24p ex2300-48p ex2300-24mp ex2300-48mp";
        junos:product-tvp "ex2300-24t ex2300-48p ex2300-48t ex2300c-12t ex2300c-12p ex2300-24t-dc";
        junos:product-tvp "ex3400-24p ex3400-24t ex3400-48p ex3400-48t";
        junos:product-tvp "ex4100-f-12t ex4100-f-12p";
        junos:product-tvp "ex4100-24t ex4100-f-24t ex4100-24p ex4100-f-24p ex4100-24mp";
        junos:product-tvp "ex4100-48t ex4100-48p ex4100-48mp ex4100-f-48t ex4100-f-48p";
        junos:product-tvp "ex4300-48mp";
        junos:product-tvp "ex4400-24x ex4400-24mp ex4400-24p ex4400-24t";
        junos:product-tvp "ex4400-48f ex4400-48mp ex4400-48p ex4400-48t";
        junos:product-tvp "qfx5120-48ym qfx5120-48t qfx5210-64c qfx5120-48y-8c ex4650-48y-8c qfx5120-32c";
        junos:product-tvp "qfx5110-24q-2p qfx5110-32q qfx5110-48s-4c qfx5110-48s-4q qfx5110-48t-6q";
        junos:product-tvp "qfx5200-48y qfx5200-32c";
    }
    augment "/oc-platform:components/oc-platform:component/" +
        "oc-platform:integrated-circuit" {
        junos:product-exclude "qfx5220-32cd qfx5220-128c qfx5130-32cd qfx5009 qfx5700 qfx5230-64cd qfx5130-48c qfx5130-48cm qfx5009 qfx5700";
    }
    augment "/oc-platform:components/oc-platform:component/" +
        "oc-platform:integrated-circuit/oc-platform:state" {
        junos:product "ptx10001-36mr ptx10004 ptx10008 ptx10016";
    }
    augment "/oc-platform:components/oc-platform:component/" +
        "oc-platform:integrated-circuit/oc-platform:state/jnx-oc-platform:properties/jnx-oc-platform:property" {
        junos:product "ptx10003-160c ptx10003-80c qfx10003-160c qfx10003-80c";
        junos:product "ptx10016 ptx10008 ptx10004";
        junos:product "ptx10001-36mr ptx10001-27cd";
    }
    augment "/oc-platform:components/oc-platform:component/" +
        "oc-platform:integrated-circuit/oc-platform:state/jnx-oc-platform:properties/jnx-oc-platform:property/jnx-oc-platform:state" {
        junos:product "ptx10003-160c ptx10003-80c";
        junos:product "qfx10003-160c qfx10003-80c";
    }
    augment "/oc-platform:components/oc-platform:component/oc-platform:state/oc-platform:location" {
        junos:product "mx304 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
    }
    augment "/oc-platform:components/oc-platform:component/oc-platform:state/oc-platform:mfg-date" {
        junos:product "mx304 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
    }
    augment "/oc-platform:components/oc-platform:component/oc-platform:state/oc-platform:hardware-version" {
        junos:product "mx304 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
    }
    augment "/oc-platform:components/oc-platform:component/oc-platform:state/oc-platform:firmware-version" {
        junos:product "mx304 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
    }
    augment "/oc-platform:components/oc-platform:component/oc-platform:state/oc-platform:software-version" {
        junos:product "ptx1000 ptx5000 ptx10001-36mr ptx10003-160c ptx10003-80c ptx10016 ptx10008 ptx10004";
        junos:product "mx960";
        junos:product "acx7908 acx7509 ACX7100-48L ACX7100-32C";
    }
    augment "/oc-platform:components/oc-platform:component/oc-platform:state/oc-platform:removable" {
        junos:product "mx304 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
    }
    augment "/oc-platform:components/oc-platform:component/oc-platform:state/oc-platform:oper-status" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
    }
    augment "/oc-platform:components/oc-platform:component/oc-platform:state/oc-platform:empty" {
        junos:product "mx304 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
    }
    augment "/oc-platform:components/oc-platform:component/oc-platform:state/oc-platform:parent" {
        junos:product "mx304 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
    }
    augment "/oc-platform:components/oc-platform:component/oc-platform:state/oc-platform:allocated-power" {
        junos:product "mx304 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
    }
    augment "/oc-platform:components/oc-platform:component/oc-platform:state/oc-platform:temperature/oc-platform:instant" {
        junos:product "ptx1000 ptx5000 ptx10001-36mr ptx10003-160c ptx10003-80c ptx10016 ptx10008 ptx10004";
        junos:product "mx960";
        junos:product "acx7908 acx7509 ACX7100-48L ACX7100-32C";
    }
    augment "/oc-platform:components/oc-platform:component/oc-platform:state/oc-platform:memory/oc-platform:available" {
        junos:product "mx304 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
    }
    augment "/oc-platform:components/oc-platform:component/oc-platform:state/oc-platform:memory/oc-platform:utilized" {
        junos:product "mx304 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
    }
    augment "/oc-platform:components/oc-platform:component/oc-platform:properties/oc-platform:property/oc-platform:state/oc-platform:configurable" {
        junos:product "ptx10001-36mr ptx10003-160c ptx10003-80c ptx10016 ptx10008 ptx10004";
        junos:product "acx7908 acx7509 ACX7100-48L ACX7100-32C";
    }
    augment "/oc-platform:components/oc-platform:component/" + "oc-linecard:linecard/oc-linecard:state" {
        junos:product "ptx10008 ptx10016";
    }
    augment "/oc-platform:components/oc-platform:component/oc-platform:properties/oc-platform:property/oc-platform:state/oc-platform:value" {
        junos:product "ptx10008 ptx10016";
        junos:product "acx7509 QFX7100-48L ACX7100-48L ACX7100-32C acx7908 ACX7024 acx7332 acx7348";
        junos:product-tvp "ex2300-24p ex2300-48p ex2300-24mp ex2300-48mp";
        junos:product-tvp "ex2300-24t ex2300-48p ex2300-48t ex2300c-12t ex2300c-12p ex2300-24t-dc";
        junos:product-tvp "ex3400-24p ex3400-24t ex3400-48p ex3400-48t";
        junos:product-tvp "ex4100-f-12t ex4100-f-12p";
        junos:product-tvp "ex4100-24t ex4100-f-24t ex4100-24p ex4100-f-24p ex4100-24mp";
        junos:product-tvp "ex4100-48t ex4100-48p ex4100-48mp ex4100-f-48t ex4100-f-48p";
        junos:product-tvp "ex4300-48mp";
        junos:product-tvp "ex4400-24x ex4400-24mp ex4400-24p ex4400-24t";
        junos:product-tvp "ex4400-48f ex4400-48mp ex4400-48p ex4400-48t";
        junos:product-tvp "qfx5120-48ym qfx5120-48t qfx5210-64c qfx5120-48y-8c ex4650-48y-8c qfx5120-32c";
        junos:product-tvp "qfx5110-24q-2p qfx5110-32q qfx5110-48s-4c qfx5110-48s-4q qfx5110-48t-6q";
        junos:product-tvp "qfx5200-48y qfx5200-32c";
    }
    augment "/oc-platform:components/oc-platform:component/" + "oc-platform:chassis" {
        junos:product "ptx10008 ptx10016";
    }
    augment "/oc-platform:components/oc-platform:component/oc-platform:power-supply/oc-platform:state" {
        junos:product "ptx10004 ptx10008 ptx10016";
    }
    augment "/oc-platform:components/oc-platform:component/oc-platform:fan/oc-platform:state" {
        junos:product "ptx10004 ptx10008 ptx10016";
    }
    augment "/oc-platform:components/oc-platform:component/oc-platform:state/oc-platform:used-power" {
        junos:product "ptx10003-160c ptx10003-80c qfx10003-160c qfx10003-80c ptx10016 ptx10008 ptx10004 ptx10001-36mr ptx10001-27cd ptx10002-36qdd";
        junos:product-exclude "mx304 mx10001 mx10002 mx960 mx480 mx240 mx5-t mx10-t mx40-t mx80 mx80-t mx80-48t mx80-p mx104 mxtsr80 mx2020 mx2010 mx2008 vmx vrr";
        junos:product "acx7908 acx7509 ACX7100-48L ACX7100-32C";
    }
    augment "/oc-platform:components/oc-platform:component/oc-platform:state/oc-platform:type" {
        junos:product "mx240 mx480 mx960 mx2010 mx2020 mx304";
        junos:product "ptx5000 ptx9000 ptx3000 sng_olive ptx1000 ptx21000 qfx10002-60c ptx10003-160c ptx10003-80c qfx10003-160c qfx10003-80c ptx10003-81cd ptx10001-36mr ptx10001-27cd ptx10002-36qdd ptx10016 ptx10008 ptx10004 qfx10016 qfx10008";
        junos:product "acx7908 acx7509 ACX7100-48L ACX7100-32C";
        junos:product-tvp "ex2300-24p ex2300-48p ex2300-24mp ex2300-48mp";
        junos:product-tvp "ex2300-24t ex2300-48p ex2300-48t ex2300c-12t ex2300c-12p ex2300-24t-dc";
        junos:product-tvp "ex3400-24p ex3400-24t ex3400-48p ex3400-48t";
        junos:product-tvp "ex4100-f-12t ex4100-f-12p";
        junos:product-tvp "ex4100-24t ex4100-f-24t ex4100-24p ex4100-f-24p ex4100-24mp";
        junos:product-tvp "ex4100-48t ex4100-48p ex4100-48mp ex4100-f-48t ex4100-f-48p";
        junos:product-tvp "ex4300-48mp";
        junos:product-tvp "ex4400-24x ex4400-24mp ex4400-24p ex4400-24t";
        junos:product-tvp "ex4400-48f ex4400-48mp ex4400-48p ex4400-48t";
        junos:product-tvp "qfx5120-48ym qfx5120-48t qfx5210-64c qfx5120-48y-8c ex4650-48y-8c qfx5120-32c";
        junos:product-tvp "qfx5110-24q-2p qfx5110-32q qfx5110-48s-4c qfx5110-48s-4q qfx5110-48t-6q";
        junos:product-tvp "qfx5200-48y qfx5200-32c";
    }
    augment "/oc-platform:components/oc-platform:component/oc-platform:integrated-circuit/oc-platform:config" {
      junos:product "ptx10001-36mr ptx10004 ptx10008 ptx10016";
    }
}
