module junos-openconfig-bfd-annotations {
  yang-version "1";
  namespace "http://yang.juniper.net/openconfig/bfd/annotations";
  prefix "jnx-oc-bfd-ann";
  import openconfig-bfd { prefix oc-bfd; }
  import junos-extension { prefix junos; }
  organization "Juniper Networks";
  description
    "This module contains augments to openconfig bfd model";
  revision "2022-05-11" {
    description "Initial revision";
    reference "0.0.1";
  }
  augment "/oc-bfd:bfd" {
      junos:product "ptx1000 ptx5000 ptx21000 ptx10003-160c ptx10003-80c qfx10003-160c qfx10003-80c ptx10003-81cd ptx10001-36mr ptx10001-27cd ptx10016 ptx10008 ptx10004 qfx5220-32cd qfx5220-128c qfx5130-32cd qfx5009 qfx5700 qfx5230-64cd qfx5130-48c qfx5130-48cm acx753 r6273 ACX7100-48L ACX7100-32C acx7509 wbonl acx7908 ACX7024 acx7332 acx7348 QFX7100-48L ptx10002-36qdd";
      junos:product "mx304 mx10001 mx10002 mx960 mx480 mx240 mx5-t mx10-t mx40-t mx80 mx80-t mx80-48t mx80-p mx104 mxtsr80 mx2020 mx2010 mx2008 vmx vrr";
      junos:product-exclude "mx5-t mx10-t mx40-t mx80 mx80-t mx80-48t mx80-p mx104 mxtsr80";
      junos:product "ptx5000 ptx9000 ptx3000 sng_olive ptx1000 ptx21000 qfx10002-60c ptx10003-160c ptx10003-80c qfx10003-160c qfx10003-80c ptx10003-81cd ptx10001-36mr ptx10001-27cd ptx10002-36qdd ptx10016 ptx10008 ptx10004 qfx10016 qfx10008";
      junos:product "acx7509 ACX7024 ACX7100-48L ACX7100-32C";
      junos:product "qfx5130-32cd qfx5220-128c qfx5220-32cd qfx5700 qfx10002-60c qfx10016 qfx10008";
      junos:product "ex9204 ex9208 ex9214 ex9251 ex9253";
      junos:product-tvp "ex2300-24p ex2300-48p ex2300-24mp ex2300-48mp";
      junos:product-tvp "qfx5120-48ym qfx5120-48t qfx5210-64c";
      junos:product-tvp "qfx5110-24q-2p qfx5110-32q qfx5110-48s-4c qfx5110-48s-4q qfx5110-48t-6q";
      junos:product-tvp "ex4100-48p ex4100-48t ex4100-24p ex4100-24t ex4100-f-48p ex4100-f-24p ex4100-f-48t ex4100-f-24t";
      junos:product-tvp "ex4100-48mp ex4100-24mp ex4100-f-12p ex4100-f-12t";
      junos:product-tvp "ex4400-24mp ex4400-24p ex4400-24t ex4400-48f ex4400-48mp ex4400-48p ex4400-48t";
      junos:product-tvp "mx10003 mx10004 mx10008 mx10016";
  }
}
