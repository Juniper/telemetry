module junos-bbe-smgd-rsmon-stats-annotations {
    yang-version 1;
    namespace "http://juniper.net/yang/junos/bbe-smgd-rsmon-stats/annotations";
    prefix "junos-bbe-smgd-rsmon-stats-ann";
    import junos-bbe-smgd-rsmon-stats { prefix junos-bbe-smgd-rsmon-stats; }
    import junos-extension { prefix junos; }
    organization "Juniper Network Inc.";
    revision "2022-09-22" {
        description "Initial version to add native bbe smgd rsmon statistics
                     related information";
    }
    augment "/junos-bbe-smgd-rsmon-stats:junos/junos-bbe-smgd-rsmon-stats:system/" +
            "junos-bbe-smgd-rsmon-stats:subscriber-management/" +
            "junos-bbe-smgd-rsmon-stats:infra/junos-bbe-smgd-rsmon-stats:resource-monitor/" +
            "junos-bbe-smgd-rsmon-stats:rsmon-infra" {
        junos:product "mx304 mx10001 mx10002 mx960 mx480 mx240 mx5-t mx10-t mx40-t mx80 mx80-t mx80-48t mx80-p mx104 mxtsr80 mx2020 mx2010 mx2008 vmx vrr";
        junos:product "ACX7100-48L ACX7100-32C";
    }
}
