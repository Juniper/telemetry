module junos-bbe-smgd-ancp-stats-annotations {
    yang-version 1;
    namespace "http://juniper.net/yang/junos/bbe-smgd-ancp-stats/annotations";
    prefix "junos-bbe-smgd-ancp-stats-ann";
    import junos-bbe-smgd-ancp-stats { prefix junos-bbe-smgd-ancp-stats; }
    import junos-extension { prefix junos; }
    organization "Juniper Network Inc.";
    revision "2022-09-22" {
        description "Initial version to add native bbe smgd ancp stats related information";
    }
    augment "/junos-bbe-smgd-ancp-stats:junos/junos-bbe-smgd-ancp-stats:system/" +
            "junos-bbe-smgd-ancp-stats:subscriber-management/" +
            "junos-bbe-smgd-ancp-stats:access-network" {
        junos:product "mx304 mx10001 mx10002 mx960 mx480 mx240 mx5-t mx10-t mx40-t mx80 mx80-t mx80-48t mx80-p mx104 mxtsr80 mx2020 mx2010 mx2008 vmx vrr";
    }
}
