module junos-state-interfaces-annotations {
    yang-version "1";
    namespace "http://yang.juniper.net/junos/state/interfaces/annotations";
    prefix "js-if-ann";
    import junos-state { prefix js; }
    import junos-state-interfaces { prefix js-if; }
    import junos-extension { prefix junos; }
    organization "Juniper Networks";
    description "Augmenting the JUNOS interfaces state supported list";
    revision "2022-12-09" {
                description "Initial revision";
            }
   augment "/js:state/js-if:interfaces" {
        junos:product-tvp "ex2300-24p ex2300-48p ex2300-24mp ex2300-48mp";
        junos:product-tvp "ex3400-24p ex3400-48p";
        junos:product-tvp "ex4300-24p ex4300-48p ex4300-48mp";
        junos:product-tvp "ex4100-48p ex4100-24p ex4100-f-48p ex4100-f-24p";
        junos:product-tvp "ex4100-48mp ex4100-24mp ex4100-f-12p";
        junos:product-tvp "ex4400-24mp ex4400-24p ex4400-48mp ex4400-48p";
    }
}
