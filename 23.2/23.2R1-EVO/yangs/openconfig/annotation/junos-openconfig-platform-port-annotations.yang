module junos-openconfig-platform-port-annotations {
    yang-version "1";
    prefix "jnx-oc-port-ann";
    namespace "http://yang.juniper.net/yang/platform/port/annotations";
    import junos-extension { prefix junos; }
    import openconfig-platform { prefix oc-platform; }
    import openconfig-platform-port { prefix oc-port; }
    organization "Juniper Networks";
    description "Augmenting the platform supported list";
    revision "2022-04-05" {
        description "Initial version to add platform supported list";
    }
    augment "/oc-platform:components/oc-platform:component/oc-platform:port/oc-port:breakout-mode/oc-port:groups/oc-port:group/oc-port:state" {
        junos:product "mx240 mx480 mx960 mx2010 mx2020 mx2008";
        junos:product "ptx10003-160c ptx10003-80c ptx10008";
        junos:product-tvp "mx10003 mx10004 mx10008 mx10016";
        junos:product-tvp "ptx10002-60c ptx1000-72q";
    }
    augment "/oc-platform:components/oc-platform:component/oc-platform:port/oc-port:breakout-mode/oc-port:groups/oc-port:group/oc-port:config/oc-port:num-breakouts" {
        junos:product "ptx10008 ptx10016";
    }
    augment "/oc-platform:components/oc-platform:component/oc-platform:port/oc-port:breakout-mode/oc-port:groups/oc-port:group/oc-port:config/oc-port:breakout-speed" {
        junos:product "ptx10008 ptx10016";
    }
}
