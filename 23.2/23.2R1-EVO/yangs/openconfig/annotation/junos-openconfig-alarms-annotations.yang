module junos-openconfig-alarms-annotations {
    yang-version "1";
    prefix "jnx-oc-alarms-ann";
    namespace "http://yang.juniper.net/openconfig/alarms/annotations";
    import junos-extension { prefix junos; }
    import openconfig-system { prefix oc-sys; }
    import openconfig-platform {prefix oc-platform; }
    import openconfig-alarm-types { prefix oc-alarm-types; }
    organization "Juniper Networks";
    description "Augmenting the sys supported list";
    revision "2022-03-28" {
        description "Initial version to add platform supported list";
    }
    augment "/oc-sys:system/oc-sys:alarms/oc-sys:alarm/oc-sys:id" {
        junos:product "ptx10001-36mr ptx10003-160c ptx10003-80c ptx10016 ptx10008 ptx10004";
    }
    augment "/oc-sys:system/oc-sys:alarms/oc-sys:alarm/oc-sys:state/oc-sys:id" {
        junos:product "ptx5000 ptx1000 ptx10001-36mr ptx10003-160c ptx10003-80c ptx10016 ptx10008 ptx10004 ptx10004 ptx10008";
        junos:product "mx304 mx960 mx2010 mx2020";
        junos:product-tvp "mx10004 mx10008 mx10016";
        junos:product "acx7908 acx7509 ACX7100-48L ACX7100-32C";
    }
    augment "/oc-sys:system/oc-sys:alarms/oc-sys:alarm/oc-sys:state/oc-sys:resource" {
        junos:product "ptx5000 ptx1000 ptx10001-36mr ptx10003-160c ptx10003-80c ptx10016 ptx10008 ptx10004 ptx10004 ptx10008";
        junos:product "mx304 mx960 mx2010 mx2020";
        junos:product-tvp "mx10004 mx10008 mx10016";
        junos:product "acx7908 acx7509 ACX7100-48L ACX7100-32C";
    }
    augment "/oc-sys:system/oc-sys:alarms/oc-sys:alarm/oc-sys:state/oc-sys:text" {
        junos:product "ptx5000 ptx1000 ptx10001-36mr ptx10003-160c ptx10003-80c ptx10016 ptx10008 ptx10004 ptx10004 ptx10008";
        junos:product "mx960";
        junos:product-tvp "mx10004 mx10008 mx10016";
        junos:product "acx7908 acx7509 ACX7100-48L ACX7100-32C";
    }
    augment "/oc-sys:system/oc-sys:alarms/oc-sys:alarm/oc-sys:state/oc-sys:time-created" {
        junos:product "ptx5000 ptx1000 ptx10001-36mr ptx10003-160c ptx10003-80c ptx10016 ptx10008 ptx10004 ptx10004 ptx10008";
        junos:product "mx304 mx960 mx2010 mx2020";
        junos:product-tvp "mx10004 mx10008 mx10016";
        junos:product "acx7908 acx7509 ACX7100-48L ACX7100-32C";
    }
    augment "/oc-sys:system/oc-sys:alarms/oc-sys:alarm/oc-sys:state/oc-sys:severity" {
        junos:product "ptx5000 ptx1000 ptx10001-36mr ptx10003-160c ptx10003-80c ptx10016 ptx10008 ptx10004 ptx10004 ptx10008";
        junos:product "mx960";
        junos:product-tvp "mx10004 mx10008 mx10016";
        junos:product "acx7908 acx7509 ACX7100-48L ACX7100-32C";
    }
    augment "/oc-sys:system/oc-sys:alarms/oc-sys:alarm/oc-sys:state/oc-sys:type-id" {
        junos:product "ptx5000 ptx1000 ptx10001-36mr ptx10003-160c ptx10003-80c ptx10016 ptx10008 ptx10004 ptx10004 ptx10008";
        junos:product "mx304 mx960 mx2010 mx2020";
        junos:product-tvp "mx10004 mx10008 mx10016";
        junos:product "acx7908 acx7509 ACX7100-48L ACX7100-32C";
    }
}
