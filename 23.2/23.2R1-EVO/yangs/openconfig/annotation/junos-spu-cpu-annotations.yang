module junos-spu-cpu-annotations {
    yang-version 1;
    namespace "http://juniper.net/yang/junos/spu-cpu/annotations";
    prefix "junos-spu-cpu-ann";
    import junos-spu-cpu { prefix junos-security; }
    import junos-extension { prefix junos; }
    organization "Juniper Network Inc.";
    revision "2022-11-10" {
        description "Initial version to add spu-cpu model product support information";
    }
      augment "/junos-security:junos/junos-security:security/junos-security:spu" {
         junos:product-tvp "NFX_SERIES";
         junos:product-tvp "srx4100 srx4200 srx4600";
         junos:product "mx240 mx480 mx960";
         junos:product-tvp "VSRX_SERIES";
         junos:product "srxtvp";
     }
      augment "/junos-security:junos/junos-security:security/junos-security:spu/junos-security:cpu" {
         junos:product-tvp "NFX_SERIES";
         junos:product-tvp "srx4100 srx4200 srx4600";
         junos:product "mx240 mx480 mx960";
         junos:product-tvp "VSRX_SERIES";
         junos:product "srxtvp";
     }
}
