module junos-openconfig-if-8021x-annotations {
  yang-version "1";
  namespace "http://yang.juniper.net/openconfig/interfaces/8021x/annotations";
  prefix "jnx-oc-8021x-ann";
  import openconfig-interfaces { prefix oc-if; }
  import openconfig-if-ethernet { prefix oc-eth; }
  import openconfig-vlan { prefix oc-vlan; }
  import openconfig-if-8021x { prefix oc-1x; }
  import junos-extension { prefix junos; }
  organization "Juniper Networks";
  description
    "This module contains augments to openconfig 802.1x model";
  revision "2023-01-11" {
    description "Initial revision";
    reference "0.0.1";
  }
  augment "/oc-if:interfaces/oc-if:interface/oc-eth:ethernet/oc-1x:dot1x" {
      junos:product "ex2200-c-12p-2g ex2200-c-12t-2g ex2200-24p-4g ex2200-24t-4g ex2200-24p-4g ex2200-24t-4g ex2200-48p-4g ex2200-48t-4g ex2200-24t-dc-4g ex3200-24t ex3200-24p ex3200-48t ex3200-48p ex4200-24f ex4200-24t ex4200-24p ex4200-48t ex4200-48p ex4200-48px ex4200-24px ex4500-40f ex4550-32f ex4550-32t ex3300-24t ex3300-24p ex3300-48p ex3300-48t ex3300-24t-dc ex3300-48t-bf ex8208 ex8216 ex6210 ex-xre ex4300-24p ex4300-24t ex4300-48p ex4300-48t ex4300-48t-bf ex4300-48t-dc ex4300-48t-dc-bf ex4300-32f dc_olive fx1600_48 fx2160_48 qfx3500 qfx3008-i fx-jvre qfx3600-16q qfx3600-i qfx5100-24q-2pf qfx5100-48s-6qf qfx5100-48t-6qf qfx5100-24q-2pi ex9204 ex9208 ex9214 ex9251 ex9253 mx304 mx10001 mx10002 mx960 mx480 mx240 mx5-t mx10-t mx40-t mx80 mx80-t mx80-48t mx80-p mx104 mxtsr80 mx2020 mx2010 mx2008 vmx vrr ptx5000 ptx9000 ptx3000 sng_olive ptx1000 ptx21000 qfx10002-60c ptx10003-160c ptx10003-80c qfx10003-160c qfx10003-80c ptx10003-81cd ptx10001-36mr ptx10001-27cd ptx10002-36qdd ptx10016 ptx10008 ptx10004 qfx10016 qfx10008 srx5800 srx5600 srx5400 acx753 r6273 ACX7100-48L ACX7100-32C acx7509 wbonl acx7908 ACX7024 acx7332 acx7348 pvi-model qfx5009 qfx5700 qfx5130-48cm";
      junos:product-exclude "srxtvp";
      junos:product-exclude "mx5-t mx10-t mx40-t mx80 mx80-t mx80-48t mx80-p mx104 mxtsr80";
      junos:product "ACX7100-48L ACX7100-32C";
      junos:product-tvp "qfx10008 qfx10016 qfx10001-l-20c";
      junos:product-tvp "qfx-5401-M20C qfx5120-48ym-8c";
      junos:product-tvp "ex3400-24p ex3400-24t ex3400-48p ex3400-48t";
      junos:product-tvp "ex4100-f-12t ex4100-f-12p";
      junos:product-tvp "ex4100-24t ex4100-f-24t ex4100-24p ex4100-f-24p ex4100-24m";
      junos:product-tvp "ex4100-48t ex4100-48p ex4100-48mp ex4100-f-48t ex4100-f-48p";
      junos:product-tvp "ex4300-48mp";
      junos:product-tvp "ex4400-24x ex4400-24mp ex4400-24p ex4400-24t";
      junos:product-tvp "ex4400-48f ex4400-48mp ex4400-48p ex4400-48t";
      junos:product-tvp "mx10004 mx10008 mx10016";
  }
  augment "/oc-if:interfaces/oc-if:interface/oc-eth:ethernet/oc-vlan:switched-vlan/oc-1x:dot1x-vlan-map" {
      junos:product "ex2200-c-12p-2g ex2200-c-12t-2g ex2200-24p-4g ex2200-24t-4g ex2200-24p-4g ex2200-24t-4g ex2200-48p-4g ex2200-48t-4g ex2200-24t-dc-4g ex3200-24t ex3200-24p ex3200-48t ex3200-48p ex4200-24f ex4200-24t ex4200-24p ex4200-48t ex4200-48p ex4200-48px ex4200-24px ex4500-40f ex4550-32f ex4550-32t ex3300-24t ex3300-24p ex3300-48p ex3300-48t ex3300-24t-dc ex3300-48t-bf ex8208 ex8216 ex6210 ex-xre ex4300-24p ex4300-24t ex4300-48p ex4300-48t ex4300-48t-bf ex4300-48t-dc ex4300-48t-dc-bf ex4300-32f dc_olive fx1600_48 fx2160_48 qfx3500 qfx3008-i fx-jvre qfx3600-16q qfx3600-i qfx5100-24q-2pf qfx5100-48s-6qf qfx5100-48t-6qf qfx5100-24q-2pi ex9204 ex9208 ex9214 ex9251 ex9253 mx304 mx10001 mx10002 mx960 mx480 mx240 mx5-t mx10-t mx40-t mx80 mx80-t mx80-48t mx80-p mx104 mxtsr80 mx2020 mx2010 mx2008 vmx vrr ptx5000 ptx9000 ptx3000 sng_olive ptx1000 ptx21000 qfx10002-60c ptx10003-160c ptx10003-80c qfx10003-160c qfx10003-80c ptx10003-81cd ptx10001-36mr ptx10001-27cd ptx10002-36qdd ptx10016 ptx10008 ptx10004 qfx10016 qfx10008 srx5800 srx5600 srx5400 acx753 r6273 ACX7100-48L ACX7100-32C acx7509 wbonl acx7908 ACX7024 acx7332 acx7348 pvi-model qfx5009 qfx5700 qfx5130-48cm";
      junos:product-exclude "srxtvp";
      junos:product-exclude "mx5-t mx10-t mx40-t mx80 mx80-t mx80-48t mx80-p mx104 mxtsr80";
      junos:product "ACX7100-48L ACX7100-32C";
      junos:product-tvp "qfx10008 qfx10016 qfx10001-l-20c";
      junos:product-tvp "qfx-5401-M20C qfx5120-48ym-8c";
      junos:product-tvp "ex3400-24p ex3400-24t ex3400-48p ex3400-48t";
      junos:product-tvp "ex4100-f-12t ex4100-f-12p";
      junos:product-tvp "ex4100-24t ex4100-f-24t ex4100-24p ex4100-f-24p ex4100-24m";
      junos:product-tvp "ex4100-48t ex4100-48p ex4100-48mp ex4100-f-48t ex4100-f-48p";
      junos:product-tvp "ex4300-48mp";
      junos:product-tvp "ex4400-24x ex4400-24mp ex4400-24p ex4400-24t";
      junos:product-tvp "ex4400-48f ex4400-48mp ex4400-48p ex4400-48t";
      junos:product-tvp "mx10004 mx10008 mx10016";
  }
  augment "/oc-if:interfaces/oc-if:interface/oc-eth:ethernet/oc-1x:authenticated-sessions" {
      junos:product "ex2200-c-12p-2g ex2200-c-12t-2g ex2200-24p-4g ex2200-24t-4g ex2200-24p-4g ex2200-24t-4g ex2200-48p-4g ex2200-48t-4g ex2200-24t-dc-4g ex3200-24t ex3200-24p ex3200-48t ex3200-48p ex4200-24f ex4200-24t ex4200-24p ex4200-48t ex4200-48p ex4200-48px ex4200-24px ex4500-40f ex4550-32f ex4550-32t ex3300-24t ex3300-24p ex3300-48p ex3300-48t ex3300-24t-dc ex3300-48t-bf ex8208 ex8216 ex6210 ex-xre ex4300-24p ex4300-24t ex4300-48p ex4300-48t ex4300-48t-bf ex4300-48t-dc ex4300-48t-dc-bf ex4300-32f dc_olive fx1600_48 fx2160_48 qfx3500 qfx3008-i fx-jvre qfx3600-16q qfx3600-i qfx5100-24q-2pf qfx5100-48s-6qf qfx5100-48t-6qf qfx5100-24q-2pi ex9204 ex9208 ex9214 ex9251 ex9253 mx304 mx10001 mx10002 mx960 mx480 mx240 mx5-t mx10-t mx40-t mx80 mx80-t mx80-48t mx80-p mx104 mxtsr80 mx2020 mx2010 mx2008 vmx vrr ptx5000 ptx9000 ptx3000 sng_olive ptx1000 ptx21000 qfx10002-60c ptx10003-160c ptx10003-80c qfx10003-160c qfx10003-80c ptx10003-81cd ptx10001-36mr ptx10001-27cd ptx10002-36qdd ptx10016 ptx10008 ptx10004 qfx10016 qfx10008 srx5800 srx5600 srx5400 acx753 r6273 ACX7100-48L ACX7100-32C acx7509 wbonl acx7908 ACX7024 acx7332 acx7348 pvi-model qfx5009 qfx5700 qfx5130-48cm";
      junos:product-exclude "srxtvp";
      junos:product-exclude "mx5-t mx10-t mx40-t mx80 mx80-t mx80-48t mx80-p mx104 mxtsr80";
      junos:product "ACX7100-48L ACX7100-32C";
      junos:product-tvp "qfx10008 qfx10016 qfx10001-l-20c";
      junos:product-tvp "qfx-5401-M20C qfx5120-48ym-8c";
      junos:product-tvp "ex3400-24p ex3400-24t ex3400-48p ex3400-48t";
      junos:product-tvp "ex4100-f-12t ex4100-f-12p";
      junos:product-tvp "ex4100-24t ex4100-f-24t ex4100-24p ex4100-f-24p ex4100-24m";
      junos:product-tvp "ex4100-48t ex4100-48p ex4100-48mp ex4100-f-48t ex4100-f-48p";
      junos:product-tvp "ex4300-48mp";
      junos:product-tvp "ex4400-24x ex4400-24mp ex4400-24p ex4400-24t";
      junos:product-tvp "ex4400-48f ex4400-48mp ex4400-48p ex4400-48t";
      junos:product-tvp "mx10004 mx10008 mx10016";
  }
}
