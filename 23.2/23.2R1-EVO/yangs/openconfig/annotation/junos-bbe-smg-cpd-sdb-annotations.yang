module junos-bbe-smg-cpd-sdb-annotations {
    yang-version 1;
    namespace "http://juniper.net/yang/junos/bbe-smg-cpd-sdb/annotations";
    prefix "junos-bbe-smg-cpd-sdb-ann";
    import junos-bbe-smg-cpd-sdb { prefix junos-bbe-smg-cpd-sdb; }
    import junos-extension { prefix junos; }
    organization "Juniper Network Inc.";
    revision "2022-09-22" {
        description "Initial version to add native bbe smg cpd sdb related information";
    }
    augment "/junos-bbe-smg-cpd-sdb:junos/junos-bbe-smg-cpd-sdb:system/" +
            "junos-bbe-smg-cpd-sdb:subscriber-management/" +
            "junos-bbe-smg-cpd-sdb:uplanes/junos-bbe-smg-cpd-sdb:uplane" {
        junos:product "cbng";
    }
}
