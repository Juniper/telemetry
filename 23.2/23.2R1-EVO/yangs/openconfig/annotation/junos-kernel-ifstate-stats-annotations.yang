module junos-kernel-ifstate-stats-annotations {
    yang-version 1;
    namespace "http://juniper.net/yang/junos/kod/annotations";
    prefix "jnx-junos-kernel-ifstate-stats-ann";
    import junos-kernel-ifstate-stats { prefix junos-kernel-ifstate-stats; }
    import junos-extension { prefix junos; }
    organization "Juniper Network Inc.";
    revision "2022-10-14" {
        description "Initial version to add kernel ifstate model product support information";
    }
    augment "/junos-kernel-ifstate-stats:junos/junos-kernel-ifstate-stats:kernel-ifstate" {
        junos:product "mx304 mx10001 mx10002 mx960 mx480 mx240 mx5-t mx10-t mx40-t mx80 mx80-t mx80-48t mx80-p mx104 mxtsr80 mx2020 mx2010 mx2008 vmx vrr";
        junos:product-exclude "mx5-t mx10-t mx40-t mx80 mx80-t mx80-48t mx80-p mx104 mxtsr80";
        junos:product "ptx5000 ptx9000 ptx3000 sng_olive ptx1000 ptx21000 qfx10002-60c ptx10003-160c ptx10003-80c qfx10003-160c qfx10003-80c ptx10003-81cd ptx10001-36mr ptx10001-27cd ptx10002-36qdd ptx10016 ptx10008 ptx10004 qfx10016 qfx10008";
        junos:product "ex9204 ex9208 ex9214 ex9251 ex9253";
    }
}
