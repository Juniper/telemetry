module junos-packet-capture-annotations {
    yang-version 1;
    namespace "http://juniper.net/yang/junos/packet-capture/annotations";
    prefix "junos-packet-capture-ann";
    import junos-packet-capture { prefix jnx-pcap; }
    import junos-extension { prefix junos; }
    organization "Juniper Network Inc.";
    revision "2023-01-25" {
        description "Initial version to add native packet capture supported list";
    }
    augment "/jnx-pcap:junos/jnx-pcap:system/jnx-pcap:linecard/jnx-pcap:packet-capture" {
        junos:product-tvp "ex4100-48p ex4100-48t ex4100-24p ex4100-24t ex4100-f-48p ex4100-f-24p ex4100-f-48t ex4100-f-24t";
        junos:product-tvp "ex4100-48mp ex4100-24mp ex4100-f-12p ex4100-f-12t";
        junos:product-tvp "ex4400-24mp ex4400-24p ex4400-24t ex4400-48f ex4400-48mp ex4400-48p ex4400-48t ex4400-24x";
    }
}
