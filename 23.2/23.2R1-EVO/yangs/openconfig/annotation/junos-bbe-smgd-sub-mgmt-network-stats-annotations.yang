module junos-bbe-smgd-sub-mgmt-network-stats-annotations {
    yang-version 1;
    namespace "http://juniper.net/yang/junos/bbe-smgd-sub-mgmt-network-stats/annotations";
    prefix "junos-bbe-smgd-sub-mgmt-network-stats-ann";
    import junos-bbe-smgd-sub-mgmt-network-stats { prefix junos-bbe-smgd-sub-mgmt-network-stats; }
    import junos-extension { prefix junos; }
    organization "Juniper Network Inc.";
    revision "2022-09-22" {
        description "Initial version to add native bbe smgd subscriber mgmt network
                     statistics related information";
    }
    augment "/junos-bbe-smgd-sub-mgmt-network-stats:junos/" +
            "junos-bbe-smgd-sub-mgmt-network-stats:system/" +
            "junos-bbe-smgd-sub-mgmt-network-stats:subscriber-management/" +
            "junos-bbe-smgd-sub-mgmt-network-stats:uplanes/" +
            "junos-bbe-smgd-sub-mgmt-network-stats:uplane" {
        junos:product "mx304 mx10001 mx10002 mx960 mx480 mx240 mx5-t mx10-t mx40-t mx80 mx80-t mx80-48t mx80-p mx104 mxtsr80 mx2020 mx2010 mx2008 vmx vrr";
        junos:product "ACX7100-48L ACX7100-32C";
        junos:product "cbng";
    }
}
