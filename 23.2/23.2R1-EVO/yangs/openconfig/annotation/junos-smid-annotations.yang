module junos-smid-annotations {
    yang-version 1;
    namespace "http://juniper.net/yang/junos/smid/annotations";
    prefix "junos-smid-ann";
    import junos-smid { prefix junos-smid; }
    import junos-extension { prefix junos; }
    organization "Juniper Network Inc.";
    revision "2022-09-22" {
        description "Initial version to add native smid model product support information";
    }
    augment "/junos-smid:junos/junos-smid:system/junos-smid:subscriber-management/" +
            "junos-smid:infra/junos-smid:sdb/junos-smid:statistics/junos-smid:state" {
        junos:product-exclude "qfx3500s qfx3600-16qs qfx5100-24q-2p qfx5100-48s-6q qfx5100-96s-8q ex4600-40f qfx5100-48t-6q qfx5100-24q-aa pvi-model qfx5200-32c-32q qfx5220-32cd qfx5220-128c qfx5130-32cd qfx5009 qfx5700 qfx5230-64cd qfx5130-48c qfx5130-48cm qfx10000-elit vqfx-10000 pvi-model qfx10004 qfx10008 qfx10016 qfx10004 qfx10008 qfx10016 dc_olive";
        junos:product-exclude "dc_olive fx-jvre qfx3500 qfx3008-i qfx3600-16q qfx3600-i qfx5100-24q-2pf qfx5100-48s-6qf qfx5100-48t-6qf qfx5100-24q-2pi";
    }
    augment "/junos-smid:junos/junos-smid:system/junos-smid:subscriber-management/" +
            "junos-smid:infra/junos-smid:sdb/junos-smid:statistics/junos-smid:client-type" {
        junos:product-exclude "qfx3500s qfx3600-16qs qfx5100-24q-2p qfx5100-48s-6q qfx5100-96s-8q ex4600-40f qfx5100-48t-6q qfx5100-24q-aa pvi-model qfx5200-32c-32q qfx5220-32cd qfx5220-128c qfx5130-32cd qfx5009 qfx5700 qfx5230-64cd qfx5130-48c qfx5130-48cm qfx10000-elit vqfx-10000 pvi-model qfx10004 qfx10008 qfx10016 qfx10004 qfx10008 qfx10016 dc_olive";
        junos:product-exclude "dc_olive fx-jvre qfx3500 qfx3008-i qfx3600-16q qfx3600-i qfx5100-24q-2pf qfx5100-48s-6qf qfx5100-48t-6qf qfx5100-24q-2pi";
    }
    augment "/junos-smid:junos/junos-smid:system/junos-smid:subscriber-management/" +
            "junos-smid:infra/junos-smid:sdb/junos-smid:statistics/junos-smid:subsystem" {
        junos:product-exclude "qfx3500s qfx3600-16qs qfx5100-24q-2p qfx5100-48s-6q qfx5100-96s-8q ex4600-40f qfx5100-48t-6q qfx5100-24q-aa pvi-model qfx5200-32c-32q qfx5220-32cd qfx5220-128c qfx5130-32cd qfx5009 qfx5700 qfx5230-64cd qfx5130-48c qfx5130-48cm qfx10000-elit vqfx-10000 pvi-model qfx10004 qfx10008 qfx10016 qfx10004 qfx10008 qfx10016 dc_olive";
        junos:product-exclude "dc_olive fx-jvre qfx3500 qfx3008-i qfx3600-16q qfx3600-i qfx5100-24q-2pf qfx5100-48s-6qf qfx5100-48t-6qf qfx5100-24q-2pi";
    }
    augment "/junos-smid:junos/junos-smid:system/junos-smid:subscriber-management/" +
            "junos-smid:infra/junos-smid:resource-monitor/junos-smid:chassis" {
        junos:product-exclude "qfx3500s qfx3600-16qs qfx5100-24q-2p qfx5100-48s-6q qfx5100-96s-8q ex4600-40f qfx5100-48t-6q qfx5100-24q-aa pvi-model qfx5200-32c-32q qfx5220-32cd qfx5220-128c qfx5130-32cd qfx5009 qfx5700 qfx5230-64cd qfx5130-48c qfx5130-48cm qfx10000-elit vqfx-10000 pvi-model qfx10004 qfx10008 qfx10016 qfx10004 qfx10008 qfx10016 dc_olive";
        junos:product-exclude "dc_olive fx-jvre qfx3500 qfx3008-i qfx3600-16q qfx3600-i qfx5100-24q-2pf qfx5100-48s-6qf qfx5100-48t-6qf qfx5100-24q-2pi";
    }
    augment "/junos-smid:junos/junos-smid:system/junos-smid:subscriber-management/" +
            "junos-smid:infra/junos-smid:resource-monitor/junos-smid:fpcs/junos-smid:fpc/" +
            "junos-smid:statistics" {
        junos:product-exclude "qfx3500s qfx3600-16qs qfx5100-24q-2p qfx5100-48s-6q qfx5100-96s-8q ex4600-40f qfx5100-48t-6q qfx5100-24q-aa pvi-model qfx5200-32c-32q qfx5220-32cd qfx5220-128c qfx5130-32cd qfx5009 qfx5700 qfx5230-64cd qfx5130-48c qfx5130-48cm qfx10000-elit vqfx-10000 pvi-model qfx10004 qfx10008 qfx10016 qfx10004 qfx10008 qfx10016 dc_olive";
        junos:product-exclude "dc_olive fx-jvre qfx3500 qfx3008-i qfx3600-16q qfx3600-i qfx5100-24q-2pf qfx5100-48s-6qf qfx5100-48t-6qf qfx5100-24q-2pi";
    }
    augment "/junos-smid:junos/junos-smid:system/junos-smid:subscriber-management/" +
            "junos-smid:infra/junos-smid:resource-monitor/junos-smid:fpcs/junos-smid:fpc/" +
            "junos-smid:pics" {
        junos:product-exclude "qfx3500s qfx3600-16qs qfx5100-24q-2p qfx5100-48s-6q qfx5100-96s-8q ex4600-40f qfx5100-48t-6q qfx5100-24q-aa pvi-model qfx5200-32c-32q qfx5220-32cd qfx5220-128c qfx5130-32cd qfx5009 qfx5700 qfx5230-64cd qfx5130-48c qfx5130-48cm qfx10000-elit vqfx-10000 pvi-model qfx10004 qfx10008 qfx10016 qfx10004 qfx10008 qfx10016 dc_olive";
        junos:product-exclude "dc_olive fx-jvre qfx3500 qfx3008-i qfx3600-16q qfx3600-i qfx5100-24q-2pf qfx5100-48s-6qf qfx5100-48t-6qf qfx5100-24q-2pi";
    }
    augment "/junos-smid:junos/junos-smid:system/junos-smid:subscriber-management/" +
            "junos-smid:chassis/junos-smid:routing-engines/junos-smid:routing-engine" {
        junos:product-exclude "qfx3500s qfx3600-16qs qfx5100-24q-2p qfx5100-48s-6q qfx5100-96s-8q ex4600-40f qfx5100-48t-6q qfx5100-24q-aa pvi-model qfx5200-32c-32q qfx5220-32cd qfx5220-128c qfx5130-32cd qfx5009 qfx5700 qfx5230-64cd qfx5130-48c qfx5130-48cm qfx10000-elit vqfx-10000 pvi-model qfx10004 qfx10008 qfx10016 qfx10004 qfx10008 qfx10016 dc_olive";
        junos:product-exclude "dc_olive fx-jvre qfx3500 qfx3008-i qfx3600-16q qfx3600-i qfx5100-24q-2pf qfx5100-48s-6qf qfx5100-48t-6qf qfx5100-24q-2pi";
    }
}
