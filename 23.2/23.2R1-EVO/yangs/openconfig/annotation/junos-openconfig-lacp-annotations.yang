module junos-openconfig-lacp-annotations {
  yang-version "1";
  namespace "http://yang.juniper.net/openconfig/lacp";
  prefix "jnx-oc-lacp-ann";
  import openconfig-lacp { prefix oc-lacp; }
  import junos-extension { prefix junos; }
  organization "Juniper Networks";
  description
     "This module contains platform annotations for LACP OC Yang";
  revision "2022-07-08" {
      description "Initial revision";
  }
  augment "/oc-lacp:lacp" {
      junos:product "ptx1000 ptx5000 ptx21000 ptx10003-160c ptx10003-80c qfx10003-160c qfx10003-80c ptx10003-81cd ptx10001-36mr ptx10001-27cd ptx10016 ptx10008 ptx10004 qfx5220-32cd qfx5220-128c qfx5130-32cd qfx5009 qfx5700 qfx5230-64cd qfx5130-48c qfx5130-48cm acx753 r6273 ACX7100-48L ACX7100-32C acx7509 wbonl acx7908 ACX7024 acx7332 acx7348 QFX7100-48L ptx10002-36qdd";
      junos:product "mx304 mx10001 mx10002 mx960 mx480 mx240 mx5-t mx10-t mx40-t mx80 mx80-t mx80-48t mx80-p mx104 mxtsr80 mx2020 mx2010 mx2008 vmx vrr";
      junos:product-exclude "mx5-t mx10-t mx40-t mx80 mx80-t mx80-48t mx80-p mx104 mxtsr80";
      junos:product "ptx5000 ptx9000 ptx3000 sng_olive ptx1000 ptx21000 qfx10002-60c ptx10003-160c ptx10003-80c qfx10003-160c qfx10003-80c ptx10003-81cd ptx10001-36mr ptx10001-27cd ptx10002-36qdd ptx10016 ptx10008 ptx10004 qfx10016 qfx10008";
      junos:product "qfx5130-32cd qfx5700 qfx10002-60c qfx10016 qfx10008 acx7900 ptx10001-36mr ptx10001-27cd";
      junos:product-tvp "TVP_EX2300_ALL TVP_EX3400_ALL TVP_EX4100_ALL TVP_EX4300_ALL TVP_EX4400_ALL TVP_EX4650_ALL";
      junos:product-tvp "TVP_QFX5K_ALL TVP_QFX10K_ALL";
      junos:product-tvp "TVP_SRX_ALL TVP_ACX_ALL TVP_MX_ALL";
      junos:product "srx5400 srx5600 srx5800 vsrx";
      junos:product-tvp "TVP_SRX_ALL";
  }
}
