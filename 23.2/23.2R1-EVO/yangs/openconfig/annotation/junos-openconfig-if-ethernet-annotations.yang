module junos-openconfig-if-ethernet-annotations {
    yang-version "1";
    prefix "jnx-oc-eth-ann";
    namespace "http://yang.juniper.net/yang/interfaces/ethernet/annotations";
    import junos-extension { prefix junos; }
    import openconfig-interfaces { prefix oc-if; }
    import openconfig-if-ethernet { prefix oc-eth; }
    organization "Juniper Networks";
    description "Augmenting the platform supported list";
    revision "2022-03-28" {
        description "Initial version to add platform supported list";
    }
    augment "/oc-if:interfaces/oc-if:interface/oc-eth:ethernet/oc-eth:config" {
        junos:product "ptx10001-36mr ptx10004 ptx10008 ptx10003-160c ptx10003-80c ptx10016";
        junos:product "mx240 mx480 mx960 mx2010 mx2020";
        junos:product "acx7509 ACX7024 ACX7100-48L ACX7100-32C acx7332 acx7348 acx7900";
        junos:product "qfx5220-32cd qfx5220-128c qfx5130-32cd qfx5009 qfx5700 qfx5230-64cd qfx5130-48c qfx5130-48cm qfx5009 qfx5700";
        junos:product-tvp "ex2300-24p ex2300-48p ex2300-24mp ex2300-48mp";
        junos:product-tvp "ex3400-24p ex3400-24t ex3400-48p ex3400-48t";
        junos:product-tvp "ex4100-f-12t ex4100-f-12p";
        junos:product-tvp "ex4100-24t ex4100-f-24t ex4100-24p ex4100-f-24p ex4100-24mp";
        junos:product-tvp "ex4100-48t ex4100-48p ex4100-48mp ex4100-f-48t ex4100-f-48p";
        junos:product-tvp "ex4300-48mp";
        junos:product-tvp "ex4400-24x ex4400-24mp ex4400-24p ex4400-24t";
        junos:product-tvp "ex4400-48f ex4400-48mp ex4400-48p ex4400-48t";
        junos:product-tvp "qfx5120-48ym qfx5120-48t qfx5210-64c qfx5120-48y-8c ex4650-48y-8c qfx5120-32c";
        junos:product-tvp "qfx5110-24q-2p qfx5110-32q qfx5110-48s-4c qfx5110-48s-4q qfx5110-48t-6q";
        junos:product-tvp "qfx5200-48y qfx5200-32c";
    }
    augment "/oc-if:interfaces/oc-if:interface/oc-eth:ethernet/oc-eth:state/oc-eth:mac-address" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
        junos:product "qfx5220-32cd qfx5220-128c qfx5130-32cd qfx5009 qfx5700 qfx5230-64cd qfx5130-48c qfx5130-48cm qfx5009 qfx5700";
    }
    augment "/oc-if:interfaces/oc-if:interface/oc-eth:ethernet/oc-eth:state/oc-eth:auto-negotiate" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
        junos:product "qfx5220-32cd qfx5220-128c qfx5130-32cd qfx5009 qfx5700 qfx5230-64cd qfx5130-48c qfx5130-48cm qfx5009 qfx5700";
    }
    augment "/oc-if:interfaces/oc-if:interface/oc-eth:ethernet/oc-eth:state/oc-eth:duplex-mode" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
        junos:product "qfx5220-32cd qfx5220-128c qfx5130-32cd qfx5009 qfx5700 qfx5230-64cd qfx5130-48c qfx5130-48cm qfx5009 qfx5700";
    }
    augment "/oc-if:interfaces/oc-if:interface/oc-eth:ethernet/oc-eth:state/oc-eth:port-speed" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
        junos:product "qfx5220-32cd qfx5220-128c qfx5130-32cd qfx5009 qfx5700 qfx5230-64cd qfx5130-48c qfx5130-48cm qfx5009 qfx5700";
        junos:product-tvp "ex2300-24p ex2300-48p ex2300-24mp ex2300-48mp";
        junos:product-tvp "ex3400-24p ex3400-24t ex3400-48p ex3400-48t";
        junos:product-tvp "ex4100-f-12t ex4100-f-12p";
        junos:product-tvp "ex4100-24t ex4100-f-24t ex4100-24p ex4100-f-24p ex4100-24mp";
        junos:product-tvp "ex4100-48t ex4100-48p ex4100-48mp ex4100-f-48t ex4100-f-48p";
        junos:product-tvp "ex4300-48mp";
        junos:product-tvp "ex4400-24x ex4400-24mp ex4400-24p ex4400-24t";
        junos:product-tvp "ex4400-48f ex4400-48mp ex4400-48p ex4400-48t";
        junos:product-tvp "qfx5120-48ym qfx5120-48t qfx5210-64c qfx5120-48y-8c ex4650-48y-8c qfx5120-32c";
        junos:product-tvp "qfx5110-24q-2p qfx5110-32q qfx5110-48s-4c qfx5110-48s-4q qfx5110-48t-6q";
        junos:product-tvp "qfx5200-48y qfx5200-32c";
    }
    augment "/oc-if:interfaces/oc-if:interface/oc-eth:ethernet/oc-eth:state/oc-eth:enable-flow-control" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
        junos:product "qfx5220-32cd qfx5220-128c qfx5130-32cd qfx5009 qfx5700 qfx5230-64cd qfx5130-48c qfx5130-48cm qfx5009 qfx5700";
    }
    augment "/oc-if:interfaces/oc-if:interface/oc-eth:ethernet/oc-eth:state/oc-eth:hw-mac-address" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
        junos:product "qfx5220-32cd qfx5220-128c qfx5130-32cd qfx5009 qfx5700 qfx5230-64cd qfx5130-48c qfx5130-48cm qfx5009 qfx5700";
        junos:product-tvp "ex2300-24p ex2300-48p ex2300-24mp ex2300-48mp";
        junos:product-tvp "ex3400-24p ex3400-24t ex3400-48p ex3400-48t";
        junos:product-tvp "ex4100-f-12t ex4100-f-12p";
        junos:product-tvp "ex4100-24t ex4100-f-24t ex4100-24p ex4100-f-24p ex4100-24mp";
        junos:product-tvp "ex4100-48t ex4100-48p ex4100-48mp ex4100-f-48t ex4100-f-48p";
        junos:product-tvp "ex4300-48mp";
        junos:product-tvp "ex4400-24x ex4400-24mp ex4400-24p ex4400-24t";
        junos:product-tvp "ex4400-48f ex4400-48mp ex4400-48p ex4400-48t";
        junos:product-tvp "qfx5120-48ym qfx5120-48t qfx5210-64c qfx5120-48y-8c ex4650-48y-8c qfx5120-32c";
        junos:product-tvp "qfx5110-24q-2p qfx5110-32q qfx5110-48s-4c qfx5110-48s-4q qfx5110-48t-6q";
        junos:product-tvp "qfx5200-48y qfx5200-32c";
    }
    augment "/oc-if:interfaces/oc-if:interface/oc-eth:ethernet/oc-eth:state/oc-eth:negotiated-duplex-mode" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
        junos:product "qfx5220-32cd qfx5220-128c qfx5130-32cd qfx5009 qfx5700 qfx5230-64cd qfx5130-48c qfx5130-48cm qfx5009 qfx5700";
        junos:product-tvp "ex2300-24p ex2300-48p ex2300-24mp ex2300-48mp";
        junos:product-tvp "ex3400-24p ex3400-24t ex3400-48p ex3400-48t";
        junos:product-tvp "ex4100-f-12t ex4100-f-12p";
        junos:product-tvp "ex4100-24t ex4100-f-24t ex4100-24p ex4100-f-24p ex4100-24mp";
        junos:product-tvp "ex4100-48t ex4100-48p ex4100-48mp ex4100-f-48t ex4100-f-48p";
        junos:product-tvp "ex4300-48mp";
        junos:product-tvp "ex4400-24x ex4400-24mp ex4400-24p ex4400-24t";
        junos:product-tvp "ex4400-48f ex4400-48mp ex4400-48p ex4400-48t";
        junos:product-tvp "qfx5120-48ym qfx5120-48t qfx5210-64c qfx5120-48y-8c ex4650-48y-8c qfx5120-32c";
        junos:product-tvp "qfx5110-24q-2p qfx5110-32q qfx5110-48s-4c qfx5110-48s-4q qfx5110-48t-6q";
        junos:product-tvp "qfx5200-48y qfx5200-32c";
    }
    augment "/oc-if:interfaces/oc-if:interface/oc-eth:ethernet/oc-eth:state/oc-eth:negotiated-port-speed" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "acx7908 acx7509 ACX7100-48L ACX7100-32C";
        junos:product "qfx5220-32cd qfx5220-128c qfx5130-32cd qfx5009 qfx5700 qfx5230-64cd qfx5130-48c qfx5130-48cm qfx5009 qfx5700";
        junos:product-tvp "ex2300-24p ex2300-48p ex2300-24mp ex2300-48mp";
        junos:product-tvp "ex3400-24p ex3400-24t ex3400-48p ex3400-48t";
        junos:product-tvp "ex4100-f-12t ex4100-f-12p";
        junos:product-tvp "ex4100-24t ex4100-f-24t ex4100-24p ex4100-f-24p ex4100-24mp";
        junos:product-tvp "ex4100-48t ex4100-48p ex4100-48mp ex4100-f-48t ex4100-f-48p";
        junos:product-tvp "ex4300-48mp";
        junos:product-tvp "ex4400-24x ex4400-24mp ex4400-24p ex4400-24t";
        junos:product-tvp "ex4400-48f ex4400-48mp ex4400-48p ex4400-48t";
        junos:product-tvp "qfx5120-48ym qfx5120-48t qfx5210-64c qfx5120-48y-8c ex4650-48y-8c qfx5120-32c";
        junos:product-tvp "qfx5110-24q-2p qfx5110-32q qfx5110-48s-4c qfx5110-48s-4q qfx5110-48t-6q";
        junos:product-tvp "qfx5200-48y qfx5200-32c";
    }
    augment "/oc-if:interfaces/oc-if:interface/oc-eth:ethernet/oc-eth:state/oc-eth:counters/oc-eth:in-mac-control-frames" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "qfx5220-32cd qfx5220-128c qfx5130-32cd qfx5009 qfx5700 qfx5230-64cd qfx5130-48c qfx5130-48cm qfx5009 qfx5700";
    }
    augment "/oc-if:interfaces/oc-if:interface/oc-eth:ethernet/oc-eth:state/oc-eth:counters/oc-eth:in-mac-pause-frames" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "qfx5220-32cd qfx5220-128c qfx5130-32cd qfx5009 qfx5700 qfx5230-64cd qfx5130-48c qfx5130-48cm qfx5009 qfx5700";
    }
    augment "/oc-if:interfaces/oc-if:interface/oc-eth:ethernet/oc-eth:state/oc-eth:counters/oc-eth:in-oversize-frames" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "qfx5220-32cd qfx5220-128c qfx5130-32cd qfx5009 qfx5700 qfx5230-64cd qfx5130-48c qfx5130-48cm qfx5009 qfx5700";
    }
    augment "/oc-if:interfaces/oc-if:interface/oc-eth:ethernet/oc-eth:state/oc-eth:counters/oc-eth:in-jabber-frames" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "qfx5220-32cd qfx5220-128c qfx5130-32cd qfx5009 qfx5700 qfx5230-64cd qfx5130-48c qfx5130-48cm qfx5009 qfx5700";
    }
    augment "/oc-if:interfaces/oc-if:interface/oc-eth:ethernet/oc-eth:state/oc-eth:counters/oc-eth:in-fragment-frames" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "qfx5220-32cd qfx5220-128c qfx5130-32cd qfx5009 qfx5700 qfx5230-64cd qfx5130-48c qfx5130-48cm qfx5009 qfx5700";
    }
    augment "/oc-if:interfaces/oc-if:interface/oc-eth:ethernet/oc-eth:state/oc-eth:counters/oc-eth:in-8021q-frames" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "qfx5220-32cd qfx5220-128c qfx5130-32cd qfx5009 qfx5700 qfx5230-64cd qfx5130-48c qfx5130-48cm qfx5009 qfx5700";
    }
    augment "/oc-if:interfaces/oc-if:interface/oc-eth:ethernet/oc-eth:state/oc-eth:counters/oc-eth:in-crc-errors" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "qfx5220-32cd qfx5220-128c qfx5130-32cd qfx5009 qfx5700 qfx5230-64cd qfx5130-48c qfx5130-48cm qfx5009 qfx5700";
    }
    augment "/oc-if:interfaces/oc-if:interface/oc-eth:ethernet/oc-eth:state/oc-eth:counters/oc-eth:in-block-errors" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "qfx5220-32cd qfx5220-128c qfx5130-32cd qfx5009 qfx5700 qfx5230-64cd qfx5130-48c qfx5130-48cm qfx5009 qfx5700";
    }
    augment "/oc-if:interfaces/oc-if:interface/oc-eth:ethernet/oc-eth:state/oc-eth:counters/oc-eth:out-mac-control-frames" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "qfx5220-32cd qfx5220-128c qfx5130-32cd qfx5009 qfx5700 qfx5230-64cd qfx5130-48c qfx5130-48cm qfx5009 qfx5700";
    }
    augment "/oc-if:interfaces/oc-if:interface/oc-eth:ethernet/oc-eth:state/oc-eth:counters/oc-eth:out-mac-pause-frames" {
        junos:product "mx240 mx304 mx480 mx960 mx2010 mx2020";
        junos:product-tvp "mx10004 mx10008 mx10016";
        junos:product "ptx1000 ptx5000 ptx10001-36mr ptx10003-160c ptx10003-80c ptx10016 ptx10008 ptx10004";
        junos:product "qfx5220-32cd qfx5220-128c qfx5130-32cd qfx5009 qfx5700 qfx5230-64cd qfx5130-48c qfx5130-48cm qfx5009 qfx5700";
    }
    augment "/oc-if:interfaces/oc-if:interface/oc-eth:ethernet/oc-eth:state/oc-eth:counters/oc-eth:out-8021q-frames" {
        junos:product-tvp "mx10004 mx10008 mx10016";
        junos:product "ptx10001-36mr ptx10003-160c ptx10003-80c ptx10016 ptx10008 ptx10004";
        junos:product "qfx5220-32cd qfx5220-128c qfx5130-32cd qfx5009 qfx5700 qfx5230-64cd qfx5130-48c qfx5130-48cm qfx5009 qfx5700";
    }
    augment "/oc-if:interfaces/oc-if:interface/oc-eth:ethernet/oc-eth:state/oc-eth:counters/oc-eth:in-maxsize-exceeded" {
        junos:product "ptx10001-36mr ptx10004 ptx10008";
        junos:product "qfx5220-32cd qfx5220-128c qfx5130-32cd qfx5009 qfx5700 qfx5230-64cd qfx5130-48c qfx5130-48cm qfx5009 qfx5700";
    }
}
