module junos-ngapd-annotations {
    yang-version 1;
    namespace "http://juniper.net/yang/junos/ngapd/annotations";
    prefix "junos-ngapd-ann";
    import junos-ngapd { prefix jngapd; }
    import junos-extension { prefix junos; }
    organization "Juniper Networks Inc.";
    revision "2022-09-28" {
        description "Initial version to add ngapd model product support information";
    }
    augment "/jngapd:junos/jngapd:system/jngapd:subscriber-management/jngapd:agf/jngapd:ngap" {
        junos:product "mx304 mx10001 mx10002 mx960 mx480 mx240 mx5-t mx10-t mx40-t mx80 mx80-t mx80-48t mx80-p mx104 mxtsr80 mx2020 mx2010 mx2008 vmx vrr";
        junos:product-exclude "mx5-t mx10-t mx40-t mx80 mx80-t mx80-48t mx80-p mx104 mxtsr80";
    }
}
