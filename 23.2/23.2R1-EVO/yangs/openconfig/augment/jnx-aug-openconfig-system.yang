module jnx-aug-openconfig-system {

  yang-version "1";

  namespace "http://yang.juniper.net/openconfig/augment/system";

  prefix "jnx-oc-system";

  import openconfig-system { prefix oc-sys; }
  import junos-extension { prefix junos; }

  organization "Juniper Networks";

  description
    "This module contains augments to openconfig system model";

  revision "2021-05-19" {
    description "Initial revision";
    reference "0.0.1";
  }

  augment "/oc-sys:system/oc-sys:ntp/oc-sys:ntp-keys/oc-sys:ntp-key/oc-sys:config" {
    uses oc-sys:system-ntp-auth-keys-config {
      refine key-value {
        junos:secret;
      }
    }
  }

  augment "/oc-sys:system/oc-sys:ntp/oc-sys:ntp-keys/oc-sys:ntp-key/oc-sys:state" {
    uses oc-sys:system-ntp-auth-keys-config {
      refine key-value {
        junos:secret;
      }
    }
  }

  augment "/oc-sys:system" {
    junos:translation-script "openconfig-system.slax openconfig-system-aaa.slax openconfig-dot1x-profile.slax";
  }
}
