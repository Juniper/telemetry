module jnx-openconfig-dev {
  yang-version "1";

  namespace "http://yang.juniper.net/openconfig/deviations"; 

  prefix "oc-dev";

  import openconfig-platform { prefix oc-platform; }
  import openconfig-platform-transceiver { prefix oc-transceiver; }
  import openconfig-terminal-device { prefix oc-opt-term; }
  import openconfig-interfaces { prefix oc-if; }
  import openconfig-if-ethernet { prefix oc-eth; }
  import openconfig-if-tunnel { prefix oc-tun; }
  import openconfig-if-ip { prefix oc-ip; }
  import openconfig-if-ip-ext { prefix oc-ip-ext; }

  import openconfig-bgp { prefix oc-bgp; }
  import openconfig-bgp-policy { prefix oc-bgp-pol; }

  import openconfig-routing-policy { prefix oc-rpol; }
  import openconfig-ospf-policy {prefix oc-ospf-pol;}

  import openconfig-acl { prefix oc-acl; }

  import ietf-inet-types { prefix inet; }
  import ietf-yang-types { prefix yang; }
  import openconfig-local-routing { prefix oc-loc-rt; }

  import openconfig-lldp { prefix oc-lldp; }

  import openconfig-vlan { prefix oc-vlan; }

  import openconfig-vlan-types { prefix oc-vlan-types; }

  import openconfig-network-instance { prefix oc-ni; }

  import openconfig-system { prefix oc-system; }

  import openconfig-lacp { prefix oc-lacp; }

  import openconfig-bfd { prefix oc-bfd; }

  import openconfig-probes { prefix oc-probes; }

  import openconfig-qos { prefix oc-qos; }

  import openconfig-macsec { prefix oc-msec; }

  import junos-yang-types { prefix jnx-types; }

  import openconfig-types { prefix oc-types; }
  import jnx-aug-openconfig-ni { prefix jnxocni; }

  import openconfig-system-grpc { prefix oc-sys-grpc; }

  import openconfig-telemetry { prefix oc-telemetry; }

  organization "Juniper Networks";
  contact "www.juniper.net";

  description
    "This module contains OpenConfig deviations for all modules";

  revision "2018-10-30" {
    description "Add deviation for specific to preference (MPLS TE)";
    reference "JUNOS 18.2X75-D30, 18.4 and above";
  }

  revision "2018-08-08" {
    description "Add deviations specific to associated-rsvp-session (MPLS TE)";
  }

  revision "2018-02-05" {
    description "add support for BGP Version 4.0.1";
    reference "TBD";
  }
  revision "2015-05-19" {
    description "Initial revision";
    reference "TBD";
  }

  deviation /oc-if:interfaces/oc-if:interface/oc-if:subinterfaces/oc-if:subinterface/oc-if:index {
       deviate replace {
           type uint32;
       }
  }

  deviation "/oc-ni:network-instances/oc-ni:network-instance/oc-ni:evpn"{
        description
          "evpn not supported";
        deviate not-supported;
  }

  deviation "/oc-ni:network-instances/oc-ni:network-instance/oc-ni:inter-instance-policies/oc-ni:import-export-policy"{
        description
          "import-export-policy not supported";
        deviate not-supported;
  }

  deviation "/oc-ni:network-instances/oc-ni:network-instance/oc-ni:route-limits"{
        description
          "route-limits not supported";
        deviate not-supported;
  }

  deviation "/oc-ni:network-instances/oc-ni:network-instance/oc-ni:interfaces/oc-ni:interface/oc-ni:config/oc-ni:irb-anycast-gateway"{
        description
          "irb-anycast-gateway not supported";
        deviate not-supported;
  }

  deviation "/oc-ni:network-instances/oc-ni:network-instance/oc-ni:fdb/oc-ni:mac-mobility"{
        description
          "mac-mobility not supported";
        deviate not-supported;
  }
  
  deviation "/oc-ni:network-instances/oc-ni:network-instance/oc-ni:fdb/oc-ni:arp-proxy"{
        description
          "arp-proxy not supported";
        deviate not-supported;
  }

  deviation "/oc-ni:network-instances/oc-ni:network-instance/oc-ni:fdb/oc-ni:nd-proxy"{
        description
          "nd-proxy not supported";
        deviate not-supported;
  }
  
  deviation "/oc-ni:network-instances/oc-ni:network-instance/oc-ni:fdb/oc-ni:config/oc-ni:anycast-gateway-mac"{
        description
          "anycast-gateway-mac not supported";
        deviate not-supported;
  }

  deviation "/oc-ni:network-instances/oc-ni:network-instance/oc-ni:fdb/oc-ni:config/oc-ni:flood-unknown-unicast-supression"{
        description
          "flood-unknown-unicast-supression not supported";
        deviate not-supported;
  }

// OSPF deviation
  deviation "/oc-ni:network-instances/oc-ni:network-instance/oc-ni:protocols/oc-ni:protocol/oc-ni:ospfv2/" +
              "oc-ni:global/oc-ni:config/oc-ni:summary-route-cost-mode"{
        description
          "Not supported in this version";
        deviate not-supported;
  }
  deviation "/oc-ni:network-instances/oc-ni:network-instance/oc-ni:protocols/oc-ni:protocol/oc-ni:ospfv2/" +
              "oc-ni:global/oc-ni:config/oc-ni:hide-transit-only-networks"{
        description
          "Not supported in this version";
        deviate not-supported;
  }
  deviation "/oc-ni:network-instances/oc-ni:network-instance/oc-ni:protocols/oc-ni:protocol/oc-ni:ospfv2/" +
              "oc-ni:global/oc-ni:timers/oc-ni:spf/oc-ni:config/oc-ni:maximum-delay"{
        description
          "Not supported in this version";
        deviate not-supported;
  }
  deviation "/oc-ni:network-instances/oc-ni:network-instance/oc-ni:protocols/oc-ni:protocol/oc-ni:ospfv2/" +
              "oc-ni:global/oc-ni:timers/oc-ni:lsa-generation"{
        description
          "Not supported in this version";
        deviate not-supported;
  }
  deviation "/oc-ni:network-instances/oc-ni:network-instance/oc-ni:protocols/oc-ni:protocol/oc-ni:ospfv2/" +
              "oc-ni:global/oc-ni:timers/oc-ni:max-metric/oc-ni:config/oc-ni:trigger"{
        description
          "Not supported in this version";
        deviate not-supported;
  }
  deviation "/oc-ni:network-instances/oc-ni:network-instance/oc-ni:protocols/oc-ni:protocol/oc-ni:ospfv2/" +
              "oc-ni:areas/oc-ni:area/oc-ni:interfaces/oc-ni:interface/oc-ni:config/oc-ni:hide-network"{
        description
          "Not supported in this version";
        deviate not-supported;
  }
  deviation "/oc-ni:network-instances/oc-ni:network-instance/oc-ni:protocols/oc-ni:protocol/oc-ni:ospfv2/" +
              "oc-ni:areas/oc-ni:area/oc-ni:interfaces/oc-ni:interface/oc-ni:lsa-filter"{
        description
          "Not supported in this version";
        deviate not-supported;
  }
  deviation "/oc-ni:network-instances/oc-ni:network-instance/oc-ni:protocols/oc-ni:protocol/oc-ni:ospfv2/" +
              "oc-ni:areas/oc-ni:area/oc-ni:interfaces/oc-ni:interface/oc-ni:neighbors/oc-ni:neighbor/oc-ni:config/oc-ni:metric"{
        description
          "Not supported in this version";
        deviate not-supported;
  }

  deviation "/oc-ni:network-instances/oc-ni:network-instance/oc-ni:protocols/oc-ni:protocol/oc-ni:ospfv2/" +
              "oc-ni:areas/oc-ni:area/oc-ni:interfaces/oc-ni:interface/oc-ni:interface-ref"{
        description
          "Not supported in this version";
        deviate not-supported;
  }
  deviation "/oc-ni:network-instances/oc-ni:network-instance/oc-ni:protocols/oc-ni:protocol/oc-ni:ospfv2/" +
              "oc-ni:global/oc-ni:mpls/oc-ni:igp-ldp-sync"{
        description
          "Not supported in this version";
        deviate not-supported;
  }
  deviation "/oc-ni:network-instances/oc-ni:network-instance/oc-ni:protocols/oc-ni:protocol/oc-ni:ospfv2/" +
              "oc-ni:global/oc-ni:inter-area-propagation-policies/oc-ni:inter-area-propagation-policy"{
        description
          "Not supported in this version";
        deviate not-supported;
  }
  deviation "/oc-ni:network-instances/oc-ni:network-instance/oc-ni:protocols/oc-ni:protocol/oc-ni:ospfv2/" +
              "oc-ni:areas/oc-ni:area/oc-ni:mpls"{
        description
          "Not supported in this version";
        deviate not-supported;
  }
  deviation "/oc-ni:network-instances/oc-ni:network-instance/oc-ni:protocols/oc-ni:protocol/oc-ni:ospfv2/" +
              "oc-ni:areas/oc-ni:area/oc-ni:interfaces/oc-ni:interface/oc-ni:config/oc-ni:multi-area-adjacency-primary"{
        description
          "Not supported in this version";
        deviate not-supported;
  }
  deviation "/oc-ni:network-instances/oc-ni:network-instance/oc-ni:protocols/oc-ni:protocol/oc-ni:ospfv2/" +
              "oc-ni:areas/oc-ni:area/oc-ni:interfaces/oc-ni:interface/oc-ni:config/oc-ni:authentication-type"{
        description
          "Not supported in this version as In Junos and RFC2328, for authentication type support,
           need to config key for md5 and password for simple password authentication type.";
        deviate not-supported;
  }
  deviation "/oc-ni:network-instances/oc-ni:network-instance/oc-ni:protocols/oc-ni:protocol/oc-ni:ospfv2/" +
              "oc-ni:areas/oc-ni:area/oc-ni:virtual-links/oc-ni:virtual-link/oc-ni:config/oc-ni:remote-router-id"{
        description
          "Not supported in this version as In Junos and RFC2328, to config virtual link with remote route id , need to config transit area also.";
        deviate not-supported;
  }
  deviation "/oc-ni:network-instances/oc-ni:network-instance/oc-ni:protocols/oc-ni:protocol/oc-ni:ospfv2/" +
              "oc-ni:global/oc-ni:state/oc-ni:summary-route-cost-mode"{
        description
          "Not supported in this version";
        deviate not-supported;
  }
  deviation "/oc-ni:network-instances/oc-ni:network-instance/oc-ni:protocols/oc-ni:protocol/oc-ni:ospfv2/" +
              "oc-ni:global/oc-ni:state/oc-ni:hide-transit-only-networks"{
        description
          "Not supported in this version";
        deviate not-supported;
  }
  deviation "/oc-ni:network-instances/oc-ni:network-instance/oc-ni:protocols/oc-ni:protocol/oc-ni:ospfv2/" +
              "oc-ni:global/oc-ni:timers/oc-ni:spf/oc-ni:state/oc-ni:maximum-delay"{
        description
          "Not supported in this version";
        deviate not-supported;
  }
  deviation "/oc-ni:network-instances/oc-ni:network-instance/oc-ni:protocols/oc-ni:protocol/oc-ni:ospfv2/" +
              "oc-ni:global/oc-ni:timers/oc-ni:spf/oc-ni:state/oc-ni:timer-type"{
        description
          "Not supported in this version";
        deviate not-supported;
  }
  deviation "/oc-ni:network-instances/oc-ni:network-instance/oc-ni:protocols/oc-ni:protocol/oc-ni:ospfv2/" +
              "oc-ni:global/oc-ni:timers/oc-ni:max-metric/oc-ni:state/oc-ni:trigger"{
        description
          "Not supported in this version";
        deviate not-supported;
  }
  deviation "/oc-ni:network-instances/oc-ni:network-instance/oc-ni:protocols/oc-ni:protocol/oc-ni:ospfv2/" +
              "oc-ni:areas/oc-ni:area/oc-ni:interfaces/oc-ni:interface/oc-ni:state/oc-ni:multi-area-adjacency-primary"{
        description
          "Not supported in this version";
        deviate not-supported;
  }
  deviation "/oc-ni:network-instances/oc-ni:network-instance/oc-ni:protocols/oc-ni:protocol/oc-ni:ospfv2/" +
              "oc-ni:areas/oc-ni:area/oc-ni:interfaces/oc-ni:interface/oc-ni:state/oc-ni:hide-network"{
        description
          "Not supported in this version";
        deviate not-supported;
  }
  deviation "/oc-ni:network-instances/oc-ni:network-instance/oc-ni:protocols/oc-ni:protocol/oc-ni:ospfv2/" +
              "oc-ni:areas/oc-ni:area/oc-ni:interfaces/oc-ni:interface/oc-ni:neighbors/oc-ni:neighbor/oc-ni:state/oc-ni:dead-time"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/" +
              "oc-ni:router-lsa/oc-ni:state/oc-ni:number-tos-metrics"{
        description
          "Not supported in this version";
        deviate not-supported;
  }

  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:router-lsa/oc-ni:types-of-service"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:summary-lsa/oc-ni:types-of-service"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:as-external-lsa"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:nssa-external-lsa"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/oc-ni:traffic-engineering"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/oc-ni:grace-lsa"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/" +
              "oc-ni:router-information/oc-ni:tlvs/oc-ni:tlv/oc-ni:unknown-tlv"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/" +
              "oc-ni:router-information/oc-ni:tlvs/oc-ni:tlv/oc-ni:informational-capabilities"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/" +
              "oc-ni:router-information/oc-ni:tlvs/oc-ni:tlv/oc-ni:node-administrative-tags"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/oc-ni:extended-prefix"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/oc-ni:extended-link"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/oc-ni:unknown-tlv"{
        description
          "Not supported in this version";
        deviate not-supported;
  }
  deviation "/oc-ni:network-instances/oc-ni:network-instance/oc-ni:protocols/oc-ni:protocol/oc-ni:ospfv2/" +
              "oc-ni:areas/oc-ni:area/oc-ni:virtual-links/oc-ni:virtual-link/oc-ni:state"{
        description
          "Not supported in this version";
        deviate not-supported;
  }

  // openconfig-vlan

  deviation "/oc-ni:network-instances/oc-ni:network-instance/oc-ni:vlans/oc-ni:vlan/oc-ni:config/oc-ni:name" {
      description
            "Junos mandates vlan name configuration.";
      deviate add {
          mandatory true;
      }
  }

  deviation "/oc-if:interfaces/oc-if:interface/oc-if:subinterfaces/oc-if:subinterface/oc-ip:ipv4/oc-ip:addresses/" +
            "oc-ip:address/oc-ip:config/oc-ip:ip" {
       deviate replace {
           type inet:ipv4-address-no-zone;
       }
  }

  deviation "/oc-if:interfaces/oc-if:interface/oc-if:subinterfaces/oc-if:subinterface/oc-ip:ipv6/oc-ip:addresses/" +
            "oc-ip:address/oc-ip:config/oc-ip:ip" {
       deviate replace {
           type inet:ipv6-address-no-zone;
       }
  }

  deviation "/oc-if:interfaces/oc-if:interface/oc-if:subinterfaces/oc-if:subinterface/oc-ip:ipv4/oc-ip:addresses/" +
            "oc-ip:address/oc-ip:ip" {
       deviate replace {
           type inet:ipv4-address-no-zone;
       }
  }

  deviation "/oc-if:interfaces/oc-if:interface/oc-if:subinterfaces/oc-if:subinterface/oc-ip:ipv6/oc-ip:addresses/" +
            "oc-ip:address/oc-ip:ip" {
       deviate replace {
           type inet:ipv6-address-no-zone;
       }
  }

  deviation "/oc-if:interfaces/oc-if:interface/oc-if:subinterfaces/oc-if:subinterface/oc-ip:ipv4/oc-ip:neighbors/" +
            "oc-ip:neighbor/oc-ip:config/oc-ip:ip" {
       deviate replace {
           type inet:ipv4-address-no-zone;
       }
  }

  deviation "/oc-if:interfaces/oc-if:interface/oc-if:subinterfaces/oc-if:subinterface/oc-ip:ipv6/oc-ip:neighbors/" +
            "oc-ip:neighbor/oc-ip:config/oc-ip:ip" {
       deviate replace {
           type inet:ipv6-address-no-zone;
       }
  }

  deviation "/oc-if:interfaces/oc-if:interface/oc-if:subinterfaces/oc-if:subinterface/oc-ip:ipv4/oc-ip:addresses/" +
            "oc-ip:address/oc-ip:vrrp/oc-ip:vrrp-group/oc-ip:config/oc-ip:virtual-address" {
       deviate replace {
           type inet:ipv4-address-no-zone;
       }
  }

  deviation "/oc-if:interfaces/oc-if:interface/oc-if:subinterfaces/oc-if:subinterface/oc-ip:ipv6/oc-ip:addresses/" +
            "oc-ip:address/oc-ip:vrrp/oc-ip:vrrp-group/oc-ip:config/oc-ip:virtual-address" {
       deviate replace {
           type inet:ipv6-address-no-zone;
       }
  }

  deviation "/oc-if:interfaces/oc-if:interface/oc-if:subinterfaces/oc-if:subinterface/oc-ip:ipv6/oc-ip:addresses/" +
            "oc-ip:address/oc-ip:vrrp/oc-ip:vrrp-group/oc-ip:config/oc-ip:virtual-link-local" {
       deviate replace {
           type inet:ipv6-address-no-zone;
       }
  }

  deviation "/oc-if:interfaces/oc-if:interface/oc-if:subinterfaces/oc-if:subinterface/oc-ip:ipv6/oc-ip:neighbors/" +
            "oc-ip:neighbor/oc-ip:state/oc-ip:is-router" {
    deviate replace {
        type boolean;
    }
    description "[adapted from IETF IP model RFC 7277]
                 Indicates that the neighbor node acts as a router.
                 Junos supports is-router as type boolean";
  }

  deviation /oc-if:interfaces/oc-if:interface/oc-if:subinterfaces/oc-if:subinterface/oc-ip:ipv6/oc-ip-ext:autoconf {
    description
          "Junos does not support ipv6 autoconf";
    deviate not-supported;
  }

  // deviate for opeconfig-interfaces.yang
  deviation /oc-if:interfaces/oc-if:interface/oc-if:state/oc-if:counters/oc-if:in-discards {
      description
          "Junos does not support in-discards at interface level";
      deviate not-supported;
  }
  deviation /oc-if:interfaces/oc-if:interface/oc-if:state/oc-if:counters/oc-if:in-unknown-protos {
      description
          "Junos does not support last-clear at interface level";
      deviate not-supported;
  }
  deviation /oc-if:interfaces/oc-if:interface/oc-if:state/oc-if:counters/oc-if:last-clear {
      description
          "Junos does not support last-clear at interface level";
      deviate not-supported;
  }

  deviation /oc-if:interfaces/oc-if:interface/oc-if:subinterfaces/oc-if:subinterface/oc-if:state/oc-if:counters/oc-if:in-broadcast-pkts {
      description
          "Junos does not support in-broadcast-pkts at subinterface level";
      deviate not-supported;
  }
  deviation /oc-if:interfaces/oc-if:interface/oc-if:subinterfaces/oc-if:subinterface/oc-if:state/oc-if:counters/oc-if:in-discards {
      description
          "Junos does not support in-discrads at subinterface level";
      deviate not-supported;
  }
  deviation /oc-if:interfaces/oc-if:interface/oc-if:subinterfaces/oc-if:subinterface/oc-if:state/oc-if:counters/oc-if:in-errors {
      description
          "Junos does not support in-errors at subinterface level";
      deviate not-supported;
  }
  deviation /oc-if:interfaces/oc-if:interface/oc-if:subinterfaces/oc-if:subinterface/oc-if:state/oc-if:counters/oc-if:in-unknown-protos {
      description
          "Junos does not support in-unknown-protos at subinterface level";
      deviate not-supported;
  }
  deviation /oc-if:interfaces/oc-if:interface/oc-if:subinterfaces/oc-if:subinterface/oc-if:state/oc-if:counters/oc-if:out-broadcast-pkts {
      description
          "Junos does not support out-broadcast-pkts at subinterface level";
      deviate not-supported;
  }
  deviation /oc-if:interfaces/oc-if:interface/oc-if:subinterfaces/oc-if:subinterface/oc-if:state/oc-if:counters/oc-if:out-discards {
      description
          "Junos does not support out-discrads at subinterface level";
      deviate not-supported;
  }
  deviation /oc-if:interfaces/oc-if:interface/oc-if:subinterfaces/oc-if:subinterface/oc-if:state/oc-if:counters/oc-if:out-errors {
      description
          "Junos does not support out-errors at subinterface level";
      deviate not-supported;
  }
  deviation /oc-if:interfaces/oc-if:interface/oc-if:subinterfaces/oc-if:subinterface/oc-if:state/oc-if:counters/oc-if:last-clear {
      description
          "Junos does not support last-clear at subinterface level";
      deviate not-supported;
  }

  deviation /oc-if:interfaces/oc-if:interface/oc-if:subinterfaces/oc-if:subinterface/oc-if:state/oc-if:counters/oc-if:carrier-transitions {
      description
          "Junos does not support carrier-transitions at subinterface level";
      deviate not-supported;
  }

  deviation /oc-if:interfaces/oc-if:interface/oc-eth:ethernet/oc-eth:state/oc-eth:counters/oc-eth:in-mac-control-frames {
      description
          "Junos does not support in-mac-control-frame at ethernet interface level";
      deviate not-supported;
  }
  deviation /oc-if:interfaces/oc-if:interface/oc-eth:ethernet/oc-eth:state/oc-eth:counters/oc-eth:in-fragment-frames {
      description
          "Junos does not support in-fragment-frames at ethernet interface level";
      deviate not-supported;
  }
  deviation /oc-if:interfaces/oc-if:interface/oc-eth:ethernet/oc-eth:state/oc-eth:counters/oc-eth:in-8021q-frames {
      description
          "Junos does not support in-8021q-frames at ethernet interface level";
      deviate not-supported;
  }
  deviation /oc-if:interfaces/oc-if:interface/oc-eth:ethernet/oc-eth:state/oc-eth:counters/oc-eth:out-mac-control-frames {
      description
          "Junos does not support out-mac-control-frames at ethernet interface level";
      deviate not-supported;
  }
  deviation /oc-if:interfaces/oc-if:interface/oc-eth:ethernet/oc-eth:state/oc-eth:counters/oc-eth:out-8021q-frames {
      description
          "Junos does not support out-8021q-frames at ethernet interface level";
      deviate not-supported;
  }

  // deviate for opeconfig-if-ip.yang
  deviation "/oc-if:interfaces/oc-if:interface/oc-if:subinterfaces/oc-if:subinterface/" +
            "oc-ip:ipv4/oc-ip:state/oc-ip:counters/oc-ip:in-error-pkts" {
    description
      "Junos does not support in-error-pkts at subinterface IPV4 family level";
    deviate not-supported;
  }
  deviation "/oc-if:interfaces/oc-if:interface/oc-if:subinterfaces/oc-if:subinterface/" +
            "oc-ip:ipv4/oc-ip:state/oc-ip:counters/oc-ip:in-discarded-pkts" {
    description
      "Junos does not support in-discarded-pkts at subinterface IPV4 family level";
    deviate not-supported;
  }
  deviation "/oc-if:interfaces/oc-if:interface/oc-if:subinterfaces/oc-if:subinterface/" +
            "oc-ip:ipv4/oc-ip:state/oc-ip:counters/oc-ip:out-error-pkts" {
    description
      "Junos does not support out-error-pkts at subinterface IPV4 family level";
    deviate not-supported;
  }
  deviation "/oc-if:interfaces/oc-if:interface/oc-if:subinterfaces/oc-if:subinterface/" +
            "oc-ip:ipv4/oc-ip:state/oc-ip:counters/oc-ip:out-discarded-pkts" {
    description
      "Junos does not support out-discarded-pkts at subinterface IPV4 family level";
    deviate not-supported;
  }
  deviation "/oc-if:interfaces/oc-if:interface/oc-if:subinterfaces/oc-if:subinterface/" +
            "oc-ip:ipv6/oc-ip:state/oc-ip:counters/oc-ip:in-error-pkts" {
    description
      "Junos does not support in-error-pkts at subinterface IPV6 family level";
    deviate not-supported;
  }
  deviation "/oc-if:interfaces/oc-if:interface/oc-if:subinterfaces/oc-if:subinterface/" +
            "oc-ip:ipv6/oc-ip:state/oc-ip:counters/oc-ip:in-discarded-pkts" {
    description
      "Junos does not support in-discarded-pkts at subinterface IPV6 family level";
    deviate not-supported;
  }
  deviation "/oc-if:interfaces/oc-if:interface/oc-if:subinterfaces/oc-if:subinterface/" +
            "oc-ip:ipv6/oc-ip:state/oc-ip:counters/oc-ip:out-error-pkts" {
    description
      "Junos does not support out-error-pkts at subinterface IPV6 family level";
    deviate not-supported;
  }
  deviation "/oc-if:interfaces/oc-if:interface/oc-if:subinterfaces/oc-if:subinterface/" +
            "oc-ip:ipv6/oc-ip:state/oc-ip:counters/oc-ip:out-discarded-pkts" {
    description
      "Junos does not support out-discarded-pkts at subinterface IPV6 family level";
    deviate not-supported;
  }

    //Network Instance

  deviation "/oc-ni:network-instances/oc-ni:network-instance/oc-ni:policy-forwarding/oc-ni:policies/oc-ni:policy/oc-ni:rules/oc-ni:rule/oc-ni:action/oc-ni:config/oc-ni:decapsulate-gre"{
        deviate not-supported;
  }

  deviation "/oc-ni:network-instances/oc-ni:network-instance/oc-ni:policy-forwarding/oc-ni:policies/oc-ni:policy/oc-ni:rules/oc-ni:rule/oc-ni:action/oc-ni:config/oc-ni:path-selection-group" {
        deviate not-supported;
  }

  deviation "/oc-ni:network-instances/oc-ni:network-instance/oc-ni:policy-forwarding/oc-ni:policies/oc-ni:policy/oc-ni:rules/oc-ni:rule/oc-ni:action/oc-ni:config/oc-ni:next-hop" {
        deviate not-supported;
  }

  deviation "/oc-ni:network-instances/oc-ni:network-instance/oc-ni:policy-forwarding/oc-ni:policies/oc-ni:policy/oc-ni:rules/oc-ni:rule/oc-ni:action/oc-ni:encapsulate-gre" {
        deviate not-supported;
  }

  deviation "/oc-ni:network-instances/oc-ni:network-instance/oc-ni:policy-forwarding/oc-ni:policies/oc-ni:policy/oc-ni:rules/oc-ni:rule/oc-ni:l2"{
        deviate not-supported;
   }

  deviation "/oc-ni:network-instances/oc-ni:network-instance/oc-ni:policy-forwarding/oc-ni:policies/oc-ni:policy/oc-ni:rules/oc-ni:rule/oc-ni:transport"{
        deviate not-supported;
   }

  deviation "/oc-ni:network-instances/oc-ni:network-instance/oc-ni:policy-forwarding/oc-ni:policies/oc-ni:policy/oc-ni:rules/oc-ni:rule/oc-ni:ipv4/oc-ni:config/oc-ni:source-address" {
      deviate replace {
          type inet:ipv4-prefix;
      }
  }

  deviation "/oc-ni:network-instances/oc-ni:network-instance/oc-ni:policy-forwarding/oc-ni:policies/oc-ni:policy/oc-ni:rules/oc-ni:rule/oc-ni:ipv4/oc-ni:config/oc-ni:destination-address" {
      deviate replace {
          type inet:ipv4-prefix;
      }
  }

  deviation "/oc-ni:network-instances/oc-ni:network-instance/oc-ni:policy-forwarding/oc-ni:policies/oc-ni:policy/oc-ni:rules/oc-ni:rule/oc-ni:ipv6/oc-ni:config/oc-ni:source-address" {
      deviate replace {
          type inet:ipv6-prefix;
      }
  }

  deviation "/oc-ni:network-instances/oc-ni:network-instance/oc-ni:policy-forwarding/oc-ni:policies/oc-ni:policy/oc-ni:rules/oc-ni:rule/oc-ni:ipv6/oc-ni:config/oc-ni:destination-address" {
      deviate replace {
          type inet:ipv6-prefix;
      }
  }

  deviation "/oc-ni:network-instances/oc-ni:network-instance/oc-ni:policy-forwarding/oc-ni:policies/oc-ni:policy/oc-ni:rules/oc-ni:rule/oc-ni:ipv4/oc-ni:config/oc-ni:dscp" {
      deviate replace {
          type string;
      }
  }


  deviation "/oc-ni:network-instances/oc-ni:network-instance/oc-ni:policy-forwarding/oc-ni:policies/oc-ni:policy/oc-ni:rules/oc-ni:rule/oc-ni:ipv6/oc-ni:config/oc-ni:dscp" {
      deviate replace {
          type string;
      }
  }

  deviation "/oc-ni:network-instances/oc-ni:network-instance/oc-ni:policy-forwarding/oc-ni:policies/oc-ni:policy/oc-ni:rules/oc-ni:rule/oc-ni:ipv6/oc-ni:config/oc-ni:destination-flow-label" {
        description
          "destination-flow-label not supported";
        deviate not-supported;
  }

  deviation "/oc-ni:network-instances/oc-ni:network-instance/oc-ni:policy-forwarding/oc-ni:policies/oc-ni:policy/oc-ni:rules/oc-ni:rule/oc-ni:ipv6/oc-ni:config/oc-ni:source-flow-label" {
        description
          "source-flow-label not supported";
        deviate not-supported;
  }

  deviation "/oc-ni:network-instances/oc-ni:network-instance/oc-ni:policy-forwarding/oc-ni:policies/oc-ni:policy/oc-ni:state" {
        description
          "policy state is not supported";
        deviate not-supported;
  }

  deviation "/oc-ni:network-instances/oc-ni:network-instance/oc-ni:policy-forwarding/oc-ni:policies/oc-ni:policy/oc-ni:rules/oc-ni:rule/oc-ni:state" {
        description
          "rule state is not supported";
        deviate not-supported;
  }

  deviation "/oc-ni:network-instances/oc-ni:network-instance/oc-ni:policy-forwarding/oc-ni:policies/oc-ni:policy/oc-ni:rules/oc-ni:rule/oc-ni:action/oc-ni:state" {
        description
          "action state is not supported";
        deviate not-supported;
  }

  deviation "/oc-ni:network-instances/oc-ni:network-instance/oc-ni:policy-forwarding/oc-ni:interfaces/oc-ni:interface/oc-ni:state" {
        description
          "interface state is not supported";
        deviate not-supported;
  }

  deviation "/oc-ni:network-instances/oc-ni:network-instance/oc-ni:policy-forwarding/oc-ni:path-selection-groups" {
        description
          "path-selection-groups is not supported";
        deviate not-supported;
  }

  // Policy Deviations

  deviation /oc-rpol:routing-policy/oc-rpol:defined-sets/oc-bgp-pol:bgp-defined-sets/oc-bgp-pol:as-path-sets {
      deviate not-supported;
  }
  deviation /oc-rpol:routing-policy/oc-rpol:defined-sets/oc-rpol:neighbor-sets/oc-rpol:neighbor-set/oc-rpol:config/oc-rpol:address {
      deviate replace {
          type inet:ip-address;
      }
  }
  deviation /oc-rpol:routing-policy/oc-rpol:policy-definitions/oc-rpol:policy-definition/oc-rpol:statements/oc-rpol:statement/oc-rpol:conditions/oc-rpol:match-prefix-set/oc-rpol:config/oc-rpol:match-set-options {
      deviate not-supported;
  }
  deviation /oc-rpol:routing-policy/oc-rpol:policy-definitions/oc-rpol:policy-definition/oc-rpol:statements/oc-rpol:statement/oc-rpol:conditions/oc-bgp-pol:bgp-conditions/oc-bgp-pol:as-path-length {
      deviate not-supported;
  }
  deviation /oc-rpol:routing-policy/oc-rpol:policy-definitions/oc-rpol:policy-definition/oc-rpol:statements/oc-rpol:statement/oc-rpol:conditions/oc-bgp-pol:bgp-conditions/oc-bgp-pol:match-as-path-set {
      deviate not-supported;
  }
  deviation /oc-rpol:routing-policy/oc-rpol:policy-definitions/oc-rpol:policy-definition/oc-rpol:statements/oc-rpol:statement/oc-rpol:conditions/oc-bgp-pol:bgp-conditions/oc-bgp-pol:config/oc-bgp-pol:next-hop-in {
      deviate replace {
        type inet:ip-address-no-zone;
      }
  }
  deviation /oc-rpol:routing-policy/oc-rpol:policy-definitions/oc-rpol:policy-definition/oc-rpol:statements/oc-rpol:statement/oc-rpol:conditions/oc-bgp-pol:bgp-conditions/oc-bgp-pol:config/oc-bgp-pol:afi-safi-in {
      deviate add {
          max-elements 1;
      }
  }
  deviation /oc-rpol:routing-policy/oc-rpol:policy-definitions/oc-rpol:policy-definition/oc-rpol:statements/oc-rpol:statement/oc-rpol:actions/oc-bgp-pol:bgp-actions/oc-bgp-pol:config/oc-bgp-pol:set-next-hop {
      deviate replace {
        type inet:ip-address-no-zone;
      }
  }
  deviation /oc-rpol:routing-policy/oc-rpol:policy-definitions/oc-rpol:policy-definition/oc-rpol:statements/oc-rpol:statement/oc-rpol:actions/oc-bgp-pol:bgp-actions/oc-bgp-pol:config/oc-bgp-pol:set-med {
      deviate replace {
         type uint32;
      }
  }
  deviation /oc-rpol:routing-policy/oc-rpol:policy-definitions/oc-rpol:policy-definition/oc-rpol:statements/oc-rpol:statement/oc-rpol:actions/oc-bgp-pol:bgp-actions/oc-bgp-pol:set-community/oc-bgp-pol:inline {
      deviate not-supported;
  }
  deviation /oc-rpol:routing-policy/oc-rpol:policy-definitions/oc-rpol:policy-definition/oc-rpol:statements/oc-rpol:statement/oc-rpol:actions/oc-bgp-pol:bgp-actions/oc-bgp-pol:set-community/oc-bgp-pol:config/oc-bgp-pol:method {
      deviate not-supported;
  }
  deviation /oc-rpol:routing-policy/oc-rpol:policy-definitions/oc-rpol:policy-definition/oc-rpol:statements/oc-rpol:statement/oc-rpol:actions/oc-bgp-pol:bgp-actions/oc-bgp-pol:set-ext-community/oc-bgp-pol:inline {
      deviate not-supported;
  }
  deviation /oc-rpol:routing-policy/oc-rpol:policy-definitions/oc-rpol:policy-definition/oc-rpol:statements/oc-rpol:statement/oc-rpol:actions/oc-bgp-pol:bgp-actions/oc-bgp-pol:set-ext-community/oc-bgp-pol:config/oc-bgp-pol:method {
      deviate not-supported;
  }
  deviation /oc-rpol:routing-policy/oc-rpol:defined-sets/oc-rpol:prefix-sets/oc-rpol:prefix-set/oc-rpol:prefixes/oc-rpol:prefix/oc-rpol:config/oc-rpol:masklength-range {
    deviate replace {
      type string {
        pattern '([0-9]+\.\.[0-9]+)|exact';
      }
    }
  }

  deviation /oc-rpol:routing-policy/oc-rpol:defined-sets/oc-rpol:prefix-sets/oc-rpol:prefix-set/oc-rpol:config/oc-rpol:mode {
      deviate not-supported;
  }


  deviation /oc-rpol:routing-policy/oc-rpol:policy-definitions/oc-rpol:policy-definition/oc-rpol:statements/oc-rpol:statement/oc-rpol:state/oc-rpol:name {
      deviate not-supported;
  }
  deviation /oc-rpol:routing-policy/oc-rpol:policy-definitions/oc-rpol:policy-definition/oc-rpol:statements/oc-rpol:statement/oc-rpol:conditions/oc-rpol:state/oc-rpol:call-policy {
      deviate not-supported;
  }
  deviation /oc-rpol:routing-policy/oc-rpol:policy-definitions/oc-rpol:policy-definition/oc-rpol:statements/oc-rpol:statement/oc-rpol:conditions/oc-rpol:state/oc-rpol:install-protocol-eq {
      deviate not-supported;
  }
  deviation /oc-rpol:routing-policy/oc-rpol:policy-definitions/oc-rpol:policy-definition/oc-rpol:statements/oc-rpol:statement/oc-rpol:conditions/oc-rpol:match-interface/oc-rpol:state/oc-rpol:interface {
      deviate not-supported;
  }
  deviation /oc-rpol:routing-policy/oc-rpol:policy-definitions/oc-rpol:policy-definition/oc-rpol:statements/oc-rpol:statement/oc-rpol:conditions/oc-rpol:match-prefix-set/oc-rpol:state/oc-rpol:prefix-set {
      deviate not-supported;
  }
  deviation /oc-rpol:routing-policy/oc-rpol:policy-definitions/oc-rpol:policy-definition/oc-rpol:statements/oc-rpol:statement/oc-rpol:conditions/oc-rpol:match-prefix-set/oc-rpol:state/oc-rpol:match-set-options {
      deviate not-supported;
  }
  deviation /oc-rpol:routing-policy/oc-rpol:policy-definitions/oc-rpol:policy-definition/oc-rpol:statements/oc-rpol:statement/oc-rpol:conditions/oc-rpol:match-neighbor-set/oc-rpol:state/oc-rpol:match-set-options {
      deviate not-supported;
  }
  deviation /oc-rpol:routing-policy/oc-rpol:policy-definitions/oc-rpol:policy-definition/oc-rpol:statements/oc-rpol:statement/oc-rpol:conditions/oc-rpol:match-tag-set/oc-rpol:state/oc-rpol:tag-set {
      deviate not-supported;
  }
  deviation /oc-rpol:routing-policy/oc-rpol:policy-definitions/oc-rpol:policy-definition/oc-rpol:statements/oc-rpol:statement/oc-rpol:conditions/oc-rpol:match-tag-set/oc-rpol:state/oc-rpol:match-set-options {
      deviate not-supported;
  }
  deviation /oc-rpol:routing-policy/oc-rpol:defined-sets/oc-rpol:neighbor-sets/oc-rpol:neighbor-set/oc-rpol:state {
      deviate not-supported;
  }
  deviation /oc-rpol:routing-policy/oc-rpol:defined-sets/oc-rpol:prefix-sets/oc-rpol:prefix-set/oc-rpol:prefixes/oc-rpol:prefix/oc-rpol:state {
      deviate not-supported;
  }
  deviation /oc-rpol:routing-policy/oc-rpol:defined-sets/oc-rpol:tag-sets/oc-rpol:tag-set/oc-rpol:state {
      deviate not-supported;
  }
  deviation /oc-rpol:routing-policy/oc-rpol:defined-sets/oc-rpol:prefix-sets/oc-rpol:prefix-set/oc-rpol:state {
      deviate not-supported;
  }
  deviation /oc-rpol:routing-policy/oc-rpol:policy-definitions/oc-rpol:policy-definition/oc-rpol:state {
      deviate not-supported;
  }
  deviation /oc-rpol:routing-policy/oc-rpol:policy-definitions/oc-rpol:policy-definition/oc-rpol:statements/oc-rpol:statement/oc-rpol:actions/oc-rpol:state {
      deviate not-supported;
  }
  deviation /oc-rpol:routing-policy/oc-rpol:policy-definitions/oc-rpol:policy-definition/oc-rpol:statements/oc-rpol:statement/oc-rpol:conditions/oc-rpol:match-interface/oc-rpol:state {
      deviate not-supported;
  }
  deviation /oc-rpol:routing-policy/oc-rpol:policy-definitions/oc-rpol:policy-definition/oc-rpol:statements/oc-rpol:statement/oc-rpol:conditions/oc-rpol:match-neighbor-set/oc-rpol:state {
      deviate not-supported;
  }
  deviation /oc-rpol:routing-policy/oc-rpol:policy-definitions/oc-rpol:policy-definition/oc-rpol:statements/oc-rpol:statement/oc-rpol:conditions/oc-rpol:match-prefix-set/oc-rpol:state {
      deviate not-supported;
  }
  deviation /oc-rpol:routing-policy/oc-rpol:policy-definitions/oc-rpol:policy-definition/oc-rpol:statements/oc-rpol:statement/oc-rpol:conditions/oc-rpol:match-tag-set/oc-rpol:state {
      deviate not-supported;
  }
  deviation /oc-rpol:routing-policy/oc-rpol:policy-definitions/oc-rpol:policy-definition/oc-rpol:statements/oc-rpol:statement/oc-rpol:conditions/oc-rpol:state {
      deviate not-supported;
  }


  // OSPF policy Deviation

  deviation "/oc-rpol:routing-policy/oc-rpol:policy-definitions/oc-rpol:policy-definition/oc-rpol:statements/oc-rpol:statement/" +
             "oc-rpol:actions/oc-ospf-pol:ospf-actions" {
      description
        "Not supported in this version";
      deviate not-supported;
  }

  deviation "/oc-rpol:routing-policy/oc-rpol:policy-definitions/oc-rpol:policy-definition/oc-rpol:statements/oc-rpol:statement/" +
             "oc-rpol:conditions/oc-ospf-pol:ospf-conditions" {
      description
        "Not supported in this version";
      deviate not-supported;
  }

  deviation /oc-ni:network-instances/oc-ni:network-instance/oc-ni:config/jnxocni:jnx-forwarding-table/jnxocni:default-export-policy {
      deviate not-supported;
  }

  // Local-Routing
  deviation /oc-loc-rt:local-routes/oc-loc-rt:static-routes/oc-loc-rt:static/oc-loc-rt:state/oc-loc-rt:prefix {
      deviate replace {
          type inet:ip-address;
      }
  }
  deviation /oc-loc-rt:local-routes/oc-loc-rt:static-routes/oc-loc-rt:static/oc-loc-rt:next-hops/oc-loc-rt:next-hop/oc-loc-rt:state/oc-loc-rt:recurse {
      deviate not-supported;
  }
  deviation /oc-loc-rt:local-routes/oc-loc-rt:local-aggregates/oc-loc-rt:aggregate/oc-loc-rt:state/oc-loc-rt:prefix {
      deviate replace {
          type inet:ip-address;
      }
  }
  
  // openconfig-lldp

  deviation /oc-lldp:lldp/oc-lldp:config/oc-lldp:system-name {
      deviate not-supported;
  }
  deviation /oc-lldp:lldp/oc-lldp:config/oc-lldp:system-description {
      deviate not-supported;
  }
  deviation /oc-lldp:lldp/oc-lldp:config/oc-lldp:chassis-id {
      deviate not-supported;
  }
  deviation /oc-lldp:lldp/oc-lldp:config/oc-lldp:chassis-id-type {
      deviate not-supported;
  }
    
  deviation "/oc-ni:network-instances/oc-ni:network-instance/oc-ni:policy-forwarding/oc-ni:interfaces/oc-ni:interface/oc-ni:interface-ref/oc-ni:config/oc-ni:interface"{
      deviate add {
          mandatory true;
      }
  }

  deviation "/oc-ni:network-instances/oc-ni:network-instance/oc-ni:policy-forwarding/oc-ni:interfaces/oc-ni:interface/oc-ni:interface-ref/oc-ni:config/oc-ni:subinterface"{
      deviate add {
          mandatory true;
      }
  }

  deviation /oc-if:interfaces/oc-if:interface/oc-if:state/oc-vlan:tpid {
    description
          "Tpid support is yet to be added.";
    deviate not-supported;
  }
    
  // Deviations of oc-vlan under oc-if

  deviation "/oc-if:interfaces/oc-if:interface/oc-if:subinterfaces/oc-if:subinterface/oc-vlan:vlan/" +
            "oc-vlan:match/oc-vlan:single-tagged-list" {
    description
      "Junos support is not yet added for single-tagged-list";
    deviate not-supported;
  }

  deviation "/oc-if:interfaces/oc-if:interface/oc-if:subinterfaces/oc-if:subinterface/oc-vlan:vlan/" +
            "oc-vlan:match/oc-vlan:single-tagged-range" {
    description
      "Junos support is not yet added for single-tagged-range";
    deviate not-supported;
  }

  deviation "/oc-if:interfaces/oc-if:interface/oc-if:subinterfaces/oc-if:subinterface/oc-vlan:vlan/" +
            "oc-vlan:match/oc-vlan:double-tagged-inner-list" {
    description
      "Junos support is not yet added for double-tagged-inner-list";
    deviate not-supported;
  }

  deviation "/oc-if:interfaces/oc-if:interface/oc-if:subinterfaces/oc-if:subinterface/oc-vlan:vlan/" +
            "oc-vlan:match/oc-vlan:double-tagged-outer-list" {
    description
      "Junos support is not yet added for double-tagged-outer-list";
    deviate not-supported;
  }

  deviation "/oc-if:interfaces/oc-if:interface/oc-if:subinterfaces/oc-if:subinterface/oc-vlan:vlan/" +
            "oc-vlan:match/oc-vlan:double-tagged-inner-range" {
    description
      "Junos support is not yet added for double-tagged-inner-range";
    deviate not-supported;
  }

  deviation "/oc-if:interfaces/oc-if:interface/oc-if:subinterfaces/oc-if:subinterface/oc-vlan:vlan/" +
            "oc-vlan:match/oc-vlan:double-tagged-outer-range" {
    description
      "Junos support is not yet added for double-tagged-outer-range";
    deviate not-supported;
  }

  deviation "/oc-if:interfaces/oc-if:interface/oc-if:subinterfaces/oc-if:subinterface/oc-vlan:vlan/" +
            "oc-vlan:match/oc-vlan:double-tagged-inner-outer-range" {
    description
      "Junos support is not yet added for double-tagged-inner-outer-range";
    deviate not-supported;
  }

  deviation "/oc-if:interfaces/oc-if:interface/oc-if:subinterfaces/oc-if:subinterface/oc-vlan:vlan/" +
            "oc-vlan:ingress-mapping" {
    description
      "Junos support is not yet added for vlan-logical-ingress-mapping";
    deviate not-supported;
  }

  deviation "/oc-if:interfaces/oc-if:interface/oc-if:subinterfaces/oc-if:subinterface/oc-vlan:vlan/" +
            "oc-vlan:egress-mapping" {
    description
      "Junos support is not yet added for vlan-logical-egress-mapping";
    deviate not-supported;
  }

  // Deviations of oc-tun under oc-if

  deviation "/oc-if:interfaces/oc-if:interface/oc-tun:tunnel/oc-tun:ipv4/oc-tun:addresses/" +
            "oc-tun:address/oc-tun:ip" {
      deviate replace {
          type inet:ipv4-address-no-zone;
      }
  }

  deviation "/oc-if:interfaces/oc-if:interface/oc-tun:tunnel/oc-tun:ipv4/oc-tun:state/oc-tun:counters" {
    description
      "Junos does not support IPv4 counters at tunnel interfaces level";
    deviate not-supported;
  }

  deviation "/oc-if:interfaces/oc-if:interface/oc-tun:tunnel/oc-tun:ipv6/oc-tun:state/oc-tun:counters" {
    description
      "Junos does not support IPv6 counters at tunnel interfaces level";
    deviate not-supported;
  }

  // NETWORK-INSTANCE Deviations

  deviation /oc-ni:network-instances/oc-ni:network-instance/oc-ni:encapsulation {
      deviate not-supported;
  }

  deviation /oc-ni:network-instances/oc-ni:network-instance/oc-ni:tables {
      deviate not-supported;
  }

  // Network instance - Segment-routing deviations

  // Te-policy
  deviation /oc-ni:network-instances/oc-ni:network-instance/oc-ni:segment-routing/oc-ni:te-policies/oc-ni:te-policy/oc-ni:state/oc-ni:name {
      deviate not-supported;
  }

  deviation /oc-ni:network-instances/oc-ni:network-instance/oc-ni:segment-routing/oc-ni:te-policies/oc-ni:te-policy/oc-ni:state/oc-ni:active {
      deviate not-supported;
  }

  deviation /oc-ni:network-instances/oc-ni:network-instance/oc-ni:segment-routing/oc-ni:te-policies/oc-ni:te-policy/oc-ni:state/oc-ni:active-since {
      deviate not-supported;
  }

  deviation /oc-ni:network-instances/oc-ni:network-instance/oc-ni:segment-routing/oc-ni:te-policies/oc-ni:te-policy/oc-ni:state/oc-ni:active-transitions {
      deviate not-supported;
  }

  deviation /oc-ni:network-instances/oc-ni:network-instance/oc-ni:segment-routing/oc-ni:te-policies/oc-ni:te-policy/oc-ni:candidate-paths/oc-ni:candidate-path/oc-ni:state/oc-ni:valid {
      deviate not-supported;
}

  deviation /oc-ni:network-instances/oc-ni:network-instance/oc-ni:segment-routing/oc-ni:te-policies/oc-ni:te-policy/oc-ni:candidate-paths/oc-ni:candidate-path/oc-ni:state/oc-ni:active {
      deviate not-supported;
  }

  deviation /oc-ni:network-instances/oc-ni:network-instance/oc-ni:segment-routing/oc-ni:te-policies/oc-ni:te-policy/oc-ni:candidate-paths/oc-ni:candidate-path/oc-ni:state/oc-ni:active-since {
      deviate not-supported;
  }

  deviation /oc-ni:network-instances/oc-ni:network-instance/oc-ni:segment-routing/oc-ni:te-policies/oc-ni:te-policy/oc-ni:candidate-paths/oc-ni:candidate-path/oc-ni:state/oc-ni:active-transitions {
      deviate not-supported;
  }

  deviation /oc-ni:network-instances/oc-ni:network-instance/oc-ni:segment-routing/oc-ni:te-policies/oc-ni:te-policy/oc-ni:candidate-paths/oc-ni:candidate-path/oc-ni:segment-lists/oc-ni:segment-list/oc-ni:sids/oc-ni:sid/oc-ni:state/oc-ni:mpls-ttl {
      deviate not-supported;
  }

  deviation /oc-ni:network-instances/oc-ni:network-instance/oc-ni:segment-routing/oc-ni:te-policies/oc-ni:te-policy/oc-ni:candidate-paths/oc-ni:candidate-path/oc-ni:segment-lists/oc-ni:segment-list/oc-ni:sids/oc-ni:sid/oc-ni:state/oc-ni:mpls-tc {
      deviate not-supported;
  }

  deviation /oc-ni:network-instances/oc-ni:network-instance/oc-ni:segment-routing/oc-ni:te-policies/oc-ni:te-policy/oc-ni:candidate-paths/oc-ni:candidate-path/oc-ni:segment-lists/oc-ni:segment-list/oc-ni:next-hops {
          deviate not-supported;
  }

  // Segment routing: sr-structural
  deviation /oc-ni:network-instances/oc-ni:network-instance/oc-ni:segment-routing/oc-ni:srgbs {
      deviate not-supported;
  }

  deviation /oc-ni:network-instances/oc-ni:network-instance/oc-ni:segment-routing/oc-ni:srlbs {
      deviate not-supported;
  }

  deviation /oc-ni:network-instances/oc-ni:network-instance/oc-ni:table-connections {
      deviate not-supported;
  }

  deviation /oc-ni:network-instances/oc-ni:network-instance/oc-ni:connection-points {
      deviate not-supported;
  }

  deviation /oc-ni:network-instances/oc-ni:network-instance/oc-ni:config/oc-ni:enabled-address-families {
      deviate not-supported;
  }

  deviation /oc-ni:network-instances/oc-ni:network-instance/oc-ni:config/oc-ni:mtu {
      deviate not-supported;
  }

  deviation /oc-ni:network-instances/oc-ni:network-instance/oc-ni:config/oc-ni:type {
      description
            "Junos does not support network-instance name without specifying network-instance type.";
      deviate add {
          mandatory true;
      }
  }

  deviation /oc-ni:network-instances/oc-ni:network-instance/oc-ni:protocols/oc-ni:protocol/oc-ni:config/oc-ni:default-metric {
      deviate not-supported;
  }

  deviation /oc-ni:network-instances/oc-ni:network-instance/oc-ni:protocols/oc-ni:protocol/oc-ni:config/oc-ni:enabled {
      deviate not-supported;
  }

  deviation /oc-ni:network-instances/oc-ni:network-instance/oc-ni:protocols/oc-ni:protocol {
      description
            "Junos does not support multiple protocol instances in a network-instance.";
      deviate add {
          unique "identifier";
      }
  }

  // ISIS deviation
  deviation  "/oc-ni:network-instances/oc-ni:network-instance/oc-ni:protocols/oc-ni:protocol" +
  "/oc-ni:isis/oc-ni:global/oc-ni:afi-safi" {
    deviate not-supported;
  }

  deviation  "/oc-ni:network-instances/oc-ni:network-instance/oc-ni:protocols/oc-ni:protocol" +
  "/oc-ni:isis/oc-ni:global/oc-ni:graceful-restart" {
    deviate not-supported;
  }

  deviation  "/oc-ni:network-instances/oc-ni:network-instance/oc-ni:protocols/oc-ni:protocol" +
  "/oc-ni:isis/oc-ni:global/oc-ni:igp-shortcuts" {
    deviate not-supported;
  }

  deviation  "/oc-ni:network-instances/oc-ni:network-instance/oc-ni:protocols/oc-ni:protocol" +
  "/oc-ni:isis/oc-ni:global/oc-ni:inter-level-propagation-policies" {
    deviate not-supported;
  }

  deviation  "/oc-ni:network-instances/oc-ni:network-instance/oc-ni:protocols/oc-ni:protocol" +
  "/oc-ni:isis/oc-ni:global/oc-ni:mpls" {
    deviate not-supported;
  }

  deviation  "/oc-ni:network-instances/oc-ni:network-instance/oc-ni:protocols/oc-ni:protocol" +
  "/oc-ni:isis/oc-ni:global/oc-ni:nsr" {
    deviate not-supported;
  }

  deviation  "/oc-ni:network-instances/oc-ni:network-instance/oc-ni:protocols/oc-ni:protocol" +
  "/oc-ni:isis/oc-ni:global/oc-ni:reference-bandwidth" {
    deviate not-supported;
  }

  deviation  "/oc-ni:network-instances/oc-ni:network-instance/oc-ni:protocols/oc-ni:protocol" +
  "/oc-ni:isis/oc-ni:global/oc-ni:segment-routing" {
    deviate not-supported;
  }

  deviation  "/oc-ni:network-instances/oc-ni:network-instance/oc-ni:protocols/oc-ni:protocol" +
  "/oc-ni:isis/oc-ni:global/oc-ni:transport" {
    deviate not-supported;
  }

  deviation  "/oc-ni:network-instances/oc-ni:network-instance/oc-ni:protocols/oc-ni:protocol" +
  "/oc-ni:isis/oc-ni:global/oc-ni:config/oc-ni:fast-flooding" {
    deviate not-supported;
  }

  deviation  "/oc-ni:network-instances/oc-ni:network-instance/oc-ni:protocols/oc-ni:protocol" +
  "/oc-ni:isis/oc-ni:global/oc-ni:config/oc-ni:iid-tlv" {
    deviate not-supported;
  }

  deviation  "/oc-ni:network-instances/oc-ni:network-instance/oc-ni:protocols/oc-ni:protocol" +
  "/oc-ni:isis/oc-ni:global/oc-ni:config/oc-ni:instance" {
    deviate not-supported;
  }

  deviation  "/oc-ni:network-instances/oc-ni:network-instance/oc-ni:protocols/oc-ni:protocol" +
  "/oc-ni:isis/oc-ni:global/oc-ni:config/oc-ni:level-capability" {
    deviate not-supported;
  }

  deviation  "/oc-ni:network-instances/oc-ni:network-instance/oc-ni:protocols/oc-ni:protocol" +
  "/oc-ni:isis/oc-ni:global/oc-ni:config/oc-ni:max-ecmp-paths" {
    deviate not-supported;
  }

  deviation  "/oc-ni:network-instances/oc-ni:network-instance/oc-ni:protocols/oc-ni:protocol" +
  "/oc-ni:isis/oc-ni:global/oc-ni:config/oc-ni:maximum-area-addresses" {
    deviate not-supported;
  }

  deviation  "/oc-ni:network-instances/oc-ni:network-instance/oc-ni:protocols/oc-ni:protocol" +
  "/oc-ni:isis/oc-ni:global/oc-ni:config/oc-ni:net" {
    deviate not-supported;
  }

  deviation  "/oc-ni:network-instances/oc-ni:network-instance/oc-ni:protocols/oc-ni:protocol" +
  "/oc-ni:isis/oc-ni:global/oc-ni:config/oc-ni:poi-tlv" {
    deviate not-supported;
  }

  deviation  "/oc-ni:network-instances/oc-ni:network-instance/oc-ni:protocols/oc-ni:protocol" +
  "/oc-ni:isis/oc-ni:global/oc-ni:config/oc-ni:hello-padding" {
    deviate not-supported;
  }

  deviation  "/oc-ni:network-instances/oc-ni:network-instance/oc-ni:protocols/oc-ni:protocol" +
  "/oc-ni:isis/oc-ni:global/oc-ni:timers/oc-ni:lsp-generation" {
    deviate not-supported;
  }

  deviation  "/oc-ni:network-instances/oc-ni:network-instance/oc-ni:protocols/oc-ni:protocol" +
  "/oc-ni:isis/oc-ni:global/oc-ni:timers/oc-ni:config/oc-ni:lsp-refresh-interval" {
    deviate not-supported;
  }

  deviation  "/oc-ni:network-instances/oc-ni:network-instance/oc-ni:protocols/oc-ni:protocol" +
  "/oc-ni:isis/oc-ni:global/oc-ni:timers/oc-ni:spf/oc-ni:config/oc-ni:spf-second-interval" {
    deviate not-supported;
  }

  deviation  "/oc-ni:network-instances/oc-ni:network-instance/oc-ni:protocols/oc-ni:protocol" +
  "/oc-ni:isis/oc-ni:global/oc-ni:lsp-bit/oc-ni:attached-bit" {
    deviate not-supported;
  }

  deviation  "/oc-ni:network-instances/oc-ni:network-instance/oc-ni:protocols/oc-ni:protocol" +
  "/oc-ni:isis/oc-ni:global/oc-ni:lsp-bit/oc-ni:overload-bit/oc-ni:reset-triggers" {
    deviate not-supported;
  }

  deviation  "/oc-ni:network-instances/oc-ni:network-instance/oc-ni:protocols/oc-ni:protocol" +
  "/oc-ni:isis/oc-ni:global/oc-ni:lsp-bit/oc-ni:overload-bit/oc-ni:config/oc-ni:advertise-high-metric" {
    deviate not-supported;
  }

  deviation  "/oc-ni:network-instances/oc-ni:network-instance/oc-ni:protocols/oc-ni:protocol" +
  "/oc-ni:isis/oc-ni:global/oc-ni:lsp-bit/oc-ni:overload-bit/oc-ni:config/oc-ni:set-bit-on-boot" {
    deviate not-supported;
  }

  deviation  "/oc-ni:network-instances/oc-ni:network-instance/oc-ni:protocols/oc-ni:protocol" +
  "/oc-ni:isis/oc-ni:interfaces/oc-ni:interface/oc-ni:levels/oc-ni:level/oc-ni:afi-safi" +
  "/oc-ni:af/oc-ni:segment-routing" {
     deviate not-supported;
  }

  deviation  "/oc-ni:network-instances/oc-ni:network-instance/oc-ni:protocols/oc-ni:protocol" +
  "/oc-ni:isis/oc-ni:interfaces/oc-ni:interface/oc-ni:levels/oc-ni:level/oc-ni:timers/oc-ni:config/oc-ni:hello-multiplier" {
    deviate not-supported;
  }

  deviation  "/oc-ni:network-instances/oc-ni:network-instance/oc-ni:protocols/oc-ni:protocol" +
  "/oc-ni:isis/oc-ni:interfaces/oc-ni:interface/oc-ni:levels/oc-ni:level/oc-ni:adjacencies" +
  "/oc-ni:adjacency/oc-ni:state/oc-ni:neighbor-ipv4-address" {
    description
      "In Junos, ISIS adjacency can have multiple ipv4 address";
    deviate not-supported;
  }

  deviation  "/oc-ni:network-instances/oc-ni:network-instance/oc-ni:protocols/oc-ni:protocol" +
  "/oc-ni:isis/oc-ni:interfaces/oc-ni:interface/oc-ni:levels/oc-ni:level/oc-ni:adjacencies" +
  "/oc-ni:adjacency/oc-ni:state/oc-ni:neighbor-ipv6-address" {
    description
      "In Junos, ISIS adjacency can have multiple ipv6 address";
    deviate not-supported;
  }

  deviation  "/oc-ni:network-instances/oc-ni:network-instance/oc-ni:protocols/oc-ni:protocol" +
  "/oc-ni:isis/oc-ni:interfaces/oc-ni:interface/oc-ni:levels/oc-ni:level/oc-ni:adjacencies" +
  "/oc-ni:adjacency/oc-ni:state/oc-ni:up-timestamp" {
    deviate not-supported;
  }

  deviation  "/oc-ni:network-instances/oc-ni:network-instance/oc-ni:protocols/oc-ni:protocol" +
  "/oc-ni:isis/oc-ni:levels/oc-ni:level/oc-ni:link-state-database/oc-ni:lsp/oc-ni:tlvs" +
  "/oc-ni:tlv/oc-ni:hostname/oc-ni:state/oc-ni:hostname" {
    description
      "In Junos and according to rfc, hostname can have single value (TLV-137) as the value field identifies the
       symbolic name of the router originating the LSP.";
    deviate not-supported;
  }

  deviation  "/oc-ni:network-instances/oc-ni:network-instance/oc-ni:protocols/oc-ni:protocol" +
  "/oc-ni:isis/oc-ni:levels/oc-ni:level/oc-ni:link-state-database/oc-ni:lsp/oc-ni:tlvs" +
  "/oc-ni:tlv/oc-ni:ipv4-te-router-id/oc-ni:state/oc-ni:router-id" {
    description
      "In Junos and according to rfc, For traffic engineering, it guarantees that we have a
       single stable address that can always be referenced in a path that will be reachable from multiple hops away,
       regardless of the state of the node's interfaces.";

    deviate not-supported;
  }

  deviation  "/oc-ni:network-instances/oc-ni:network-instance/oc-ni:protocols/oc-ni:protocol" +
  "/oc-ni:isis/oc-ni:levels/oc-ni:level/oc-ni:link-state-database/oc-ni:lsp/oc-ni:tlvs" +
  "/oc-ni:tlv/oc-ni:extended-is-reachability/oc-ni:neighbors/oc-ni:neighbor/oc-ni:instances/oc-ni:instance" +
  "/oc-ni:state/oc-ni:id" {

    deviate not-supported;
  }


  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv6-te-router-id" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:instance-ids" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv6-srlgs" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:purge-oi" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:is-reachability" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv4-internal-reachability" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv4-external-reachability" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:authentication" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:multi-topology" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:isis-neighbor-attribute" {
     
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:mt-isis-neighbor-attribute" {
     
      deviate not-supported;
  }  

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:is-alias-id" {
     
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:mt-isn" {
     
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:mt-ipv4-reachability" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:mt-ipv6-reachability" {

      deviate not-supported;
  }
  
  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:instances/oc-ni:instance/oc-ni:subtlvs/oc-ni:subtlv" +
  "/oc-ni:link-attributes" {

      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:instances/oc-ni:instance/oc-ni:subtlvs/oc-ni:subtlv" +
  "/oc-ni:link-protection-type" {

      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:instances/oc-ni:instance/oc-ni:subtlvs/oc-ni:subtlv" +
  "/oc-ni:unconstrained-lsp" {

      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:instances/oc-ni:instance/oc-ni:subtlvs/oc-ni:subtlv" +
  "/oc-ni:link-delay" {

      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:instances/oc-ni:instance/oc-ni:subtlvs/oc-ni:subtlv" +
  "/oc-ni:min-max-link-delay" {

      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:instances/oc-ni:instance/oc-ni:subtlvs/oc-ni:subtlv" +
  "/oc-ni:link-delay-variation" {

      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:instances/oc-ni:instance/oc-ni:subtlvs/oc-ni:subtlv" +
  "/oc-ni:link-loss" {

      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:instances/oc-ni:instance/oc-ni:subtlvs/oc-ni:subtlv" +
  "/oc-ni:residual-bandwidth" {

      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:instances/oc-ni:instance/oc-ni:subtlvs/oc-ni:subtlv" +
  "/oc-ni:available-bandwidth" {

      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:instances/oc-ni:instance/oc-ni:subtlvs/oc-ni:subtlv" +
  "/oc-ni:utilized-bandwidth" {

      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-ipv4-reachability/oc-ni:prefixes/oc-ni:prefix/oc-ni:subtlvs/oc-ni:subtlv" +
  "/oc-ni:tag64" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-ipv4-reachability/oc-ni:prefixes/oc-ni:prefix/oc-ni:subtlvs/oc-ni:subtlv" +
  "/oc-ni:flags" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-ipv4-reachability/oc-ni:prefixes/oc-ni:prefix/oc-ni:subtlvs/oc-ni:subtlv" +
  "/oc-ni:ipv4-source-router-id" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-ipv4-reachability/oc-ni:prefixes/oc-ni:prefix/oc-ni:subtlvs/oc-ni:subtlv" +
  "/oc-ni:ipv6-source-router-id" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv6-reachability/oc-ni:prefixes/oc-ni:prefix/oc-ni:subtlvs/oc-ni:subtlv" +
  "/oc-ni:tag64" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv6-reachability/oc-ni:prefixes/oc-ni:prefix/oc-ni:subtlvs/oc-ni:subtlv" +
  "/oc-ni:flags" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv6-reachability/oc-ni:prefixes/oc-ni:prefix/oc-ni:subtlvs/oc-ni:subtlv" +
  "/oc-ni:ipv4-source-router-id" {
      
      deviate not-supported;
  } 

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv6-reachability/oc-ni:prefixes/oc-ni:prefix/oc-ni:subtlvs/oc-ni:subtlv" +
  "/oc-ni:ipv6-source-router-id" {

      deviate not-supported;
  }

  deviation "/oc-ni:network-instances/oc-ni:network-instance/oc-ni:protocols/oc-ni:protocol" +
  "/oc-ni:isis/oc-ni:levels/oc-ni:level/oc-ni:authentication" {
      deviate not-supported;
  }

  deviation "/oc-ni:network-instances/oc-ni:network-instance/oc-ni:protocols/oc-ni:protocol" +
  "/oc-ni:isis/oc-ni:interfaces/oc-ni:interface/oc-ni:levels/oc-ni:level/oc-ni:packet-counters" {
      description
          "Openconfig needs to update the OC model because the level number of 
           unknown packet-type is not known. And in case of hello packet 
           sent/received in ppmd, only interface information is present and 
           these packets are not sent to rpd from ppmd. Thus, the packet-counters
           are added per interface, instead of per level. The OC version in this
           case is ISIS OC v0.3.3.
          ";
      deviate not-supported;    
  }

  deviation "/oc-ni:network-instances/oc-ni:network-instance/oc-ni:protocols/oc-ni:protocol" +
  "/oc-ni:isis/oc-ni:levels/oc-ni:level/oc-ni:state/oc-ni:enabled" {
      
      deviate not-supported;
  }

  deviation "/oc-ni:network-instances/oc-ni:network-instance/oc-ni:protocols/oc-ni:protocol" +
  "/oc-ni:isis/oc-ni:levels/oc-ni:level/oc-ni:state/oc-ni:metric-style" {
      
      deviate not-supported;
  }

  deviation "/oc-ni:network-instances/oc-ni:network-instance/oc-ni:protocols/oc-ni:protocol" +
  "/oc-ni:isis/oc-ni:levels/oc-ni:level/oc-ni:state/oc-ni:authentication-check" {
      
      deviate not-supported;
  }

  deviation "/oc-ni:network-instances/oc-ni:network-instance/oc-ni:protocols/oc-ni:protocol" +
  "/oc-ni:isis/oc-ni:levels/oc-ni:level/oc-ni:traffic-engineering" {
      
      deviate not-supported;
  }

  deviation "/oc-ni:network-instances/oc-ni:network-instance/oc-ni:protocols/oc-ni:protocol" +
  "/oc-ni:isis/oc-ni:levels/oc-ni:level/oc-ni:route-preference" {
      
      deviate not-supported;
  }

  deviation "/oc-ni:network-instances/oc-ni:network-instance/oc-ni:protocols/oc-ni:protocol" +
  "/oc-ni:isis/oc-ni:levels/oc-ni:level/oc-ni:system-level-counters" {

      deviate not-supported;
  }

  deviation "/oc-ni:network-instances/oc-ni:network-instance/oc-ni:protocols/oc-ni:protocol" +
  "/oc-ni:isis/oc-ni:levels/oc-ni:level/oc-ni:config/oc-ni:authentication-check" {

      deviate not-supported;
  }

  deviation "/oc-ni:network-instances/oc-ni:network-instance/oc-ni:protocols/oc-ni:protocol" +
  "/oc-ni:isis/oc-ni:levels/oc-ni:level/oc-ni:config/oc-ni:level-number" {

      deviate not-supported;
  }

  deviation "/oc-ni:network-instances/oc-ni:network-instance/oc-ni:protocols/oc-ni:protocol" +
  "/oc-ni:isis/oc-ni:interfaces/oc-ni:interface/oc-ni:state/oc-ni:passive" {
      
      deviate not-supported;
  }

  deviation "/oc-ni:network-instances/oc-ni:network-instance/oc-ni:protocols/oc-ni:protocol" +
  "/oc-ni:isis/oc-ni:interfaces/oc-ni:interface/oc-ni:circuit-counters" {

      deviate not-supported;
  }

  deviation "/oc-ni:network-instances/oc-ni:network-instance/oc-ni:protocols/oc-ni:protocol" +
  "/oc-ni:isis/oc-ni:interfaces/oc-ni:interface/oc-ni:config/oc-ni:hello-padding" {

      deviate not-supported;
  }

  deviation "/oc-ni:network-instances/oc-ni:network-instance/oc-ni:protocols/oc-ni:protocol" +
  "/oc-ni:isis/oc-ni:interfaces/oc-ni:interface/oc-ni:config/oc-ni:interface-id" {

      deviate not-supported;
  }

  deviation "/oc-ni:network-instances/oc-ni:network-instance/oc-ni:protocols/oc-ni:protocol" +
  "/oc-ni:isis/oc-ni:interfaces/oc-ni:interface/oc-ni:config/oc-ni:passive" {

      deviate not-supported;
  }

  deviation "/oc-ni:network-instances/oc-ni:network-instance/oc-ni:protocols/oc-ni:protocol" +
  "/oc-ni:isis/oc-ni:interfaces/oc-ni:interface/oc-ni:state/oc-ni:hello-padding" {
      
      deviate not-supported;
  }

  deviation "/oc-ni:network-instances/oc-ni:network-instance/oc-ni:protocols/oc-ni:protocol" +
  "/oc-ni:isis/oc-ni:interfaces/oc-ni:interface/oc-ni:state/oc-ni:circuit-type" {
      
      deviate not-supported;
  }

  deviation "/oc-ni:network-instances/oc-ni:network-instance/oc-ni:protocols/oc-ni:protocol" +
  "/oc-ni:isis/oc-ni:interfaces/oc-ni:interface/oc-ni:afi-safi" {
      
      deviate not-supported;
  }

  deviation "/oc-ni:network-instances/oc-ni:network-instance/oc-ni:protocols/oc-ni:protocol" +
  "/oc-ni:isis/oc-ni:interfaces/oc-ni:interface/oc-ni:levels/oc-ni:level/oc-ni:config" {
      
      deviate not-supported;
  }

  deviation "/oc-ni:network-instances/oc-ni:network-instance/oc-ni:protocols/oc-ni:protocol" +
  "/oc-ni:isis/oc-ni:interfaces/oc-ni:interface/oc-ni:levels/oc-ni:level/oc-ni:state" +
  "/oc-ni:passive" {
      
      deviate not-supported;
  }

  deviation "/oc-ni:network-instances/oc-ni:network-instance/oc-ni:protocols/oc-ni:protocol" +
  "/oc-ni:isis/oc-ni:interfaces/oc-ni:interface/oc-ni:levels/oc-ni:level/oc-ni:state" +
  "/oc-ni:priority" {
      
      deviate not-supported;
  }

  deviation "/oc-ni:network-instances/oc-ni:network-instance/oc-ni:protocols/oc-ni:protocol" +
  "/oc-ni:isis/oc-ni:interfaces/oc-ni:interface/oc-ni:levels/oc-ni:level/oc-ni:state" +
  "/oc-ni:enabled" {
      
      deviate not-supported;
  }

  deviation "/oc-ni:network-instances/oc-ni:network-instance/oc-ni:protocols/oc-ni:protocol" +
  "/oc-ni:isis/oc-ni:interfaces/oc-ni:interface/oc-ni:levels/oc-ni:level" +
  "/oc-ni:hello-authentication" {

      deviate not-supported;
  }

  deviation "/oc-ni:network-instances/oc-ni:network-instance/oc-ni:protocols/oc-ni:protocol" +
  "/oc-ni:isis/oc-ni:interfaces/oc-ni:interface/oc-ni:bfd/oc-ni:config" {

      deviate not-supported;
  }

  deviation "/oc-ni:network-instances/oc-ni:network-instance/oc-ni:protocols/oc-ni:protocol" +
  "/oc-ni:isis/oc-ni:interfaces/oc-ni:interface/oc-ni:interface-ref" {
      
      deviate not-supported;
  }

 deviation /oc-if:interfaces/oc-if:interface/oc-if:config/oc-if:type {
    description
        "Right now multi-level identityref is not supported in Junos,
         Till this support is added, we can't use identityref for leaf type";
    deviate replace {
       type string;
    }
 }

  // Network-Instance - MPLS Deviations
  
  // Global
  deviation /oc-ni:network-instances/oc-ni:network-instance/oc-ni:mpls/oc-ni:global/oc-ni:state/oc-ni:null-label{
      deviate not-supported;
  }
  deviation /oc-ni:network-instances/oc-ni:network-instance/oc-ni:mpls/oc-ni:global/oc-ni:interface-attributes/oc-ni:interface/oc-ni:state/oc-ni:interface-id {
      deviate not-supported;
  }
  deviation /oc-ni:network-instances/oc-ni:network-instance/oc-ni:mpls/oc-ni:global/oc-ni:interface-attributes/oc-ni:interface/oc-ni:state/oc-ni:mpls-enabled {
      deviate not-supported;
  }
  deviation /oc-ni:network-instances/oc-ni:network-instance/oc-ni:mpls/oc-ni:global/oc-ni:interface-attributes/oc-ni:interface/oc-ni:interface-ref {
      deviate not-supported;
  }
  deviation /oc-ni:network-instances/oc-ni:network-instance/oc-ni:mpls/oc-ni:global/oc-ni:reserved-label-blocks/oc-ni:reserved-label-block/oc-ni:state/oc-ni:local-id {
      deviate not-supported;
  }
  deviation /oc-ni:network-instances/oc-ni:network-instance/oc-ni:mpls/oc-ni:global/oc-ni:reserved-label-blocks/oc-ni:reserved-label-block/oc-ni:state/oc-ni:lower-bound {
      deviate not-supported;
  }
  deviation /oc-ni:network-instances/oc-ni:network-instance/oc-ni:mpls/oc-ni:global/oc-ni:reserved-label-blocks/oc-ni:reserved-label-block/oc-ni:state/oc-ni:upper-bound {
      deviate not-supported;
  }
  deviation /oc-ni:network-instances/oc-ni:network-instance/oc-ni:mpls/oc-ni:global/oc-ni:config/oc-ni:pw-encapsulation {
      deviate not-supported;
      description "Not supported in this release";
  }
  deviation /oc-ni:network-instances/oc-ni:network-instance/oc-ni:mpls/oc-ni:global/oc-ni:state/oc-ni:pw-encapsulation {
      deviate not-supported;
      description "Not supported in this release";
  }
  deviation /oc-ni:network-instances/oc-ni:network-instance/oc-ni:mpls/oc-ni:global/oc-ni:config/oc-ni:ttl-propagation {
      deviate not-supported;
      description "Not supported in this release";
  }
  deviation /oc-ni:network-instances/oc-ni:network-instance/oc-ni:mpls/oc-ni:global/oc-ni:state/oc-ni:ttl-propagation {
      deviate not-supported;
      description "Not supported in this release";
  }
  
  // Signaling-Protocols

  deviation /oc-ni:network-instances/oc-ni:network-instance/oc-ni:mpls/oc-ni:signaling-protocols/oc-ni:ldp/oc-ni:global/oc-ni:graceful-restart/oc-ni:state/oc-ni:forwarding-holdtime {
      deviate not-supported;
  }
  deviation /oc-ni:network-instances/oc-ni:network-instance/oc-ni:mpls/oc-ni:signaling-protocols/oc-ni:ldp/oc-ni:neighbors/oc-ni:neighbor/oc-ni:hello-adjacencies/oc-ni:hello-adjacency/oc-ni:state/oc-ni:hello-received {
      deviate not-supported;
  }
  deviation /oc-ni:network-instances/oc-ni:network-instance/oc-ni:mpls/oc-ni:signaling-protocols/oc-ni:ldp/oc-ni:neighbors/oc-ni:neighbor/oc-ni:hello-adjacencies/oc-ni:hello-adjacency/oc-ni:state/oc-ni:hello-dropped {
      deviate not-supported;
  }
  deviation /oc-ni:network-instances/oc-ni:network-instance/oc-ni:mpls/oc-ni:signaling-protocols/oc-ni:ldp/oc-ni:neighbors/oc-ni:neighbor/oc-ni:hello-adjacencies/oc-ni:hello-adjacency/oc-ni:hello-holdtime/oc-ni:state/oc-ni:next-hello {
      deviate not-supported;
  }

  deviation /oc-ni:network-instances/oc-ni:network-instance/oc-ni:mpls/oc-ni:signaling-protocols/oc-ni:segment-routing {
      deviate not-supported;
  }

  deviation /oc-ni:network-instances/oc-ni:network-instance/oc-ni:mpls/oc-ni:signaling-protocols/oc-ni:ldp/oc-ni:global/oc-ni:graceful-restart/oc-ni:config/oc-ni:forwarding-holdtime {
       deviate not-supported;
  }
  deviation /oc-ni:network-instances/oc-ni:network-instance/oc-ni:mpls/oc-ni:signaling-protocols/oc-ni:ldp/oc-ni:interface-attributes/oc-ni:interfaces/oc-ni:interface/oc-ni:interface-ref/oc-ni:config {
       deviate not-supported;
   }
    deviation /oc-ni:network-instances/oc-ni:network-instance/oc-ni:mpls/oc-ni:signaling-protocols/oc-ni:ldp/oc-ni:interface-attributes/oc-ni:interfaces/oc-ni:interface/oc-ni:address-families/oc-ni:address-family/oc-ni:config {
       deviate not-supported;
   }
   deviation /oc-ni:network-instances/oc-ni:network-instance/oc-ni:mpls/oc-ni:signaling-protocols/oc-ni:ldp/oc-ni:targeted/oc-ni:address-families/oc-ni:address-family/oc-ni:config {
       deviate not-supported;
   }
   deviation /oc-ni:network-instances/oc-ni:network-instance/oc-ni:mpls/oc-ni:signaling-protocols/oc-ni:ldp/oc-ni:targeted/oc-ni:address-families/oc-ni:address-family/oc-ni:targets/oc-ni:target/oc-ni:config {
       deviate not-supported;
   }

  // Signaling-Protocols - RSVP - Global
  deviation /oc-ni:network-instances/oc-ni:network-instance/oc-ni:mpls/oc-ni:signaling-protocols/oc-ni:rsvp-te/oc-ni:global/oc-ni:hellos/oc-ni:config/oc-ni:hello-interval {
      deviate replace {
          type uint16 {
              range 1..60;
          }
          units seconds;
          default 9;
      }
  }
  deviation /oc-ni:network-instances/oc-ni:network-instance/oc-ni:mpls/oc-ni:signaling-protocols/oc-ni:rsvp-te/oc-ni:global/oc-ni:soft-preemption/oc-ni:config/oc-ni:soft-preemption-timeout {
      deviate replace {
          type uint16 {
              range 1..180;
          }
          default 30;
      }
  }
  deviation /oc-ni:network-instances/oc-ni:network-instance/oc-ni:mpls/oc-ni:signaling-protocols/oc-ni:rsvp-te/oc-ni:global/oc-ni:graceful-restart/oc-ni:config/oc-ni:restart-time {
      deviate replace {
          type uint32 {
              range 1..1800;
          }
      }
  }
  deviation /oc-ni:network-instances/oc-ni:network-instance/oc-ni:mpls/oc-ni:signaling-protocols/oc-ni:rsvp-te/oc-ni:global/oc-ni:graceful-restart/oc-ni:config/oc-ni:recovery-time {
      deviate replace {
          type uint32 {
              range 1..3600;
          }
      }
  }

  // Signaling-Protocols - RSVP - Sessions
  deviation /oc-ni:network-instances/oc-ni:network-instance/oc-ni:mpls/oc-ni:signaling-protocols/oc-ni:rsvp-te/oc-ni:sessions/oc-ni:session/oc-ni:state/oc-ni:local-index {
      deviate replace {
          type uint32;
      }
  }
  deviation /oc-ni:network-instances/oc-ni:network-instance/oc-ni:mpls/oc-ni:signaling-protocols/oc-ni:rsvp-te/oc-ni:sessions/oc-ni:session/oc-ni:state/oc-ni:sender-tspec/oc-ni:rate {
      deviate replace {
          type string;
      }
  }
  deviation /oc-ni:network-instances/oc-ni:network-instance/oc-ni:mpls/oc-ni:signaling-protocols/oc-ni:rsvp-te/oc-ni:sessions/oc-ni:session/oc-ni:state/oc-ni:sender-tspec/oc-ni:size {
      deviate replace {
          type string;
      }
  }
  deviation /oc-ni:network-instances/oc-ni:network-instance/oc-ni:mpls/oc-ni:signaling-protocols/oc-ni:rsvp-te/oc-ni:sessions/oc-ni:session/oc-ni:state/oc-ni:sender-tspec/oc-ni:peak-data-rate {
      deviate replace {
          type string;
      }
  }
  deviation /oc-ni:network-instances/oc-ni:network-instance/oc-ni:mpls/oc-ni:signaling-protocols/oc-ni:rsvp-te/oc-ni:sessions/oc-ni:session/oc-ni:explicit-route-objects/oc-ni:explicit-route-object/oc-ni:state/oc-ni:asn {
      deviate not-supported;
  }
  deviation /oc-ni:network-instances/oc-ni:network-instance/oc-ni:mpls/oc-ni:signaling-protocols/oc-ni:rsvp-te/oc-ni:sessions/oc-ni:session/oc-ni:explicit-route-objects/oc-ni:explicit-route-object/oc-ni:state/oc-ni:label {
      deviate not-supported;
  }

  // Signaling-Protocols - RSVP - Interface Attributes
  deviation /oc-ni:network-instances/oc-ni:network-instance/oc-ni:mpls/oc-ni:signaling-protocols/oc-ni:rsvp-te/oc-ni:interface-attributes/oc-ni:interface/oc-ni:hellos/oc-ni:config/oc-ni:hello-interval {
      deviate replace {
          type uint16 {
              range 1..60;
          }
          units seconds;
          default 9;
      }
  }
  deviation /oc-ni:network-instances/oc-ni:network-instance/oc-ni:mpls/oc-ni:signaling-protocols/oc-ni:rsvp-te/oc-ni:interface-attributes/oc-ni:interface/oc-ni:authentication/oc-ni:config/oc-ni:authentication-key {
      deviate replace {
          type string {
              length 1..16;
          }
      }
  }
  deviation /oc-ni:network-instances/oc-ni:network-instance/oc-ni:mpls/oc-ni:signaling-protocols/oc-ni:rsvp-te/oc-ni:interface-attributes/oc-ni:interface/oc-ni:interface-ref {
      deviate not-supported;
  }
  deviation /oc-ni:network-instances/oc-ni:network-instance/oc-ni:mpls/oc-ni:signaling-protocols/oc-ni:rsvp-te/oc-ni:interface-attributes/oc-ni:interface/oc-ni:state/oc-ni:counters/oc-ni:errors/oc-ni:transmit-queue-full {
      deviate not-supported;
  }
  deviation /oc-ni:network-instances/oc-ni:network-instance/oc-ni:mpls/oc-ni:signaling-protocols/oc-ni:rsvp-te/oc-ni:interface-attributes/oc-ni:interface/oc-ni:state/oc-ni:counters/oc-ni:rate-limited-messages {
      deviate not-supported;
  }
  deviation /oc-ni:network-instances/oc-ni:network-instance/oc-ni:mpls/oc-ni:signaling-protocols/oc-ni:rsvp-te/oc-ni:interface-attributes/oc-ni:interface/oc-ni:bandwidth-reservations/oc-ni:bandwidth-reservation/oc-ni:state/oc-ni:available-bandwidth {
      deviate replace {
          type uint64;
      }
      deviate add {
          units "bps";
      }
  }
  deviation /oc-ni:network-instances/oc-ni:network-instance/oc-ni:mpls/oc-ni:signaling-protocols/oc-ni:rsvp-te/oc-ni:interface-attributes/oc-ni:interface/oc-ni:bandwidth-reservations/oc-ni:bandwidth-reservation/oc-ni:state/oc-ni:highwater-mark {
      deviate replace {
          type uint64;
      }
      deviate add {
          units "bps";
      }
  }
  deviation /oc-ni:network-instances/oc-ni:network-instance/oc-ni:mpls/oc-ni:signaling-protocols/oc-ni:rsvp-te/oc-ni:interface-attributes/oc-ni:interface/oc-ni:bandwidth-reservations/oc-ni:bandwidth-reservation/oc-ni:state/oc-ni:reserved-bandwidth {
      deviate replace {
          type uint64;
      }
      deviate add {
          units "bps";
      }
  }
  // TE Global Attributes
  deviation /oc-ni:network-instances/oc-ni:network-instance/oc-ni:mpls/oc-ni:te-global-attributes/oc-ni:srlgs/oc-ni:srlg/oc-ni:static-srlg-members/oc-ni:members-list/oc-ni:config/oc-ni:to-address {
	  deviate replace {
		  type inet:ip-address;
	  }
  }
  deviation /oc-ni:network-instances/oc-ni:network-instance/oc-ni:mpls/oc-ni:te-global-attributes/oc-ni:srlgs/oc-ni:srlg/oc-ni:config/oc-ni:cost {
      deviate replace {
          type uint32 {
              range 1..65535;
          }
      }
  }
  deviation /oc-ni:network-instances/oc-ni:network-instance/oc-ni:mpls/oc-ni:te-global-attributes/oc-ni:srlgs/oc-ni:srlg/oc-ni:config/oc-ni:value {
      deviate replace {
          type uint32 {
              range 1..max;
          }
      }
  }
  deviation /oc-ni:network-instances/oc-ni:network-instance/oc-ni:mpls/oc-ni:te-global-attributes/oc-ni:srlgs/oc-ni:srlg/oc-ni:config/oc-ni:name {
      deviate replace {
          type string {
              length 1..64;
          }
      }
  }
  deviation /oc-ni:network-instances/oc-ni:network-instance/oc-ni:mpls/oc-ni:te-global-attributes/oc-ni:te-lsp-timers/oc-ni:config/oc-ni:install-delay {
      deviate replace {
          type uint16 {
              range 1..900;
          }
      }
  }
  // TE Interface Attributes
  deviation /oc-ni:network-instances/oc-ni:network-instance/oc-ni:mpls/oc-ni:te-interface-attributes/oc-ni:interface/oc-ni:config/oc-ni:te-metric {
      deviate not-supported;
  }
  deviation /oc-ni:network-instances/oc-ni:network-instance/oc-ni:mpls/oc-ni:te-interface-attributes/oc-ni:interface/oc-ni:igp-flooding-bandwidth/oc-ni:config/oc-ni:threshold-specification {
      deviate not-supported;
  }
  deviation /oc-ni:network-instances/oc-ni:network-instance/oc-ni:mpls/oc-ni:te-interface-attributes/oc-ni:interface/oc-ni:igp-flooding-bandwidth/oc-ni:config/oc-ni:delta-percentage {
      deviate replace {
        type uint8 {
            range 1..20;
        }
      }
  }
  deviation /oc-ni:network-instances/oc-ni:network-instance/oc-ni:mpls/oc-ni:te-interface-attributes/oc-ni:interface/oc-ni:igp-flooding-bandwidth/oc-ni:config/oc-ni:up-thresholds {
      deviate not-supported;
  }
  deviation /oc-ni:network-instances/oc-ni:network-instance/oc-ni:mpls/oc-ni:te-interface-attributes/oc-ni:interface/oc-ni:igp-flooding-bandwidth/oc-ni:config/oc-ni:down-thresholds {
      deviate not-supported;
  }
  deviation /oc-ni:network-instances/oc-ni:network-instance/oc-ni:mpls/oc-ni:te-interface-attributes/oc-ni:interface/oc-ni:igp-flooding-bandwidth/oc-ni:config/oc-ni:up-down-thresholds {
      deviate not-supported;
  }
  // LSPs
  deviation /oc-ni:network-instances/oc-ni:network-instance/oc-ni:mpls/oc-ni:lsps/oc-ni:static-lsps {
      deviate not-supported;
  }
  deviation /oc-ni:network-instances/oc-ni:network-instance/oc-ni:mpls/oc-ni:lsps/oc-ni:unconstrained-path {
      deviate not-supported;
  }
  deviation /oc-ni:network-instances/oc-ni:network-instance/oc-ni:mpls/oc-ni:lsps/oc-ni:constrained-path/oc-ni:named-explicit-paths/oc-ni:named-explicit-path/oc-ni:config/oc-ni:name {
      deviate replace {
          type string {
              length 1..64;
          }
      }
  }
  deviation /oc-ni:network-instances/oc-ni:network-instance/oc-ni:mpls/oc-ni:lsps/oc-ni:constrained-path/oc-ni:named-explicit-paths/oc-ni:named-explicit-path/oc-ni:config/oc-ni:sid-selection-mode {
      deviate not-supported;
      description "Not supported in this release.";
  }
  deviation /oc-ni:network-instances/oc-ni:network-instance/oc-ni:mpls/oc-ni:lsps/oc-ni:constrained-path/oc-ni:named-explicit-paths/oc-ni:named-explicit-path/oc-ni:config/oc-ni:sid-protection-required {
      deviate not-supported;
      description "Not supported in this release.";
  }
  deviation /oc-ni:network-instances/oc-ni:network-instance/oc-ni:mpls/oc-ni:lsps/oc-ni:constrained-path/oc-ni:tunnels/oc-ni:tunnel/oc-ni:config/oc-ni:name {
      deviate replace {
          type string {
              length 1..64;
          }
      }
  }
  deviation /oc-ni:network-instances/oc-ni:network-instance/oc-ni:mpls/oc-ni:lsps/oc-ni:constrained-path/oc-ni:tunnels/oc-ni:tunnel/oc-ni:config/oc-ni:type {
      deviate not-supported;
  }
  deviation /oc-ni:network-instances/oc-ni:network-instance/oc-ni:mpls/oc-ni:lsps/oc-ni:constrained-path/oc-ni:tunnels/oc-ni:tunnel/oc-ni:config/oc-ni:signaling-protocol {
      deviate not-supported;
  }
  deviation /oc-ni:network-instances/oc-ni:network-instance/oc-ni:mpls/oc-ni:lsps/oc-ni:constrained-path/oc-ni:tunnels/oc-ni:tunnel/oc-ni:config/oc-ni:metric-type {
      deviate not-supported;
  }
  deviation /oc-ni:network-instances/oc-ni:network-instance/oc-ni:mpls/oc-ni:lsps/oc-ni:constrained-path/oc-ni:tunnels/oc-ni:tunnel/oc-ni:config/oc-ni:metric {
      deviate replace {
          type int32 {
              range 1..16777215;
          }
      }
  }
  deviation /oc-ni:network-instances/oc-ni:network-instance/oc-ni:mpls/oc-ni:lsps/oc-ni:constrained-path/oc-ni:tunnels/oc-ni:tunnel/oc-ni:config/oc-ni:shortcut-eligible {
      deviate not-supported;
  }
  deviation /oc-ni:network-instances/oc-ni:network-instance/oc-ni:mpls/oc-ni:lsps/oc-ni:constrained-path/oc-ni:tunnels/oc-ni:tunnel/oc-ni:bandwidth/oc-ni:config/oc-ni:set-bandwidth {
      deviate replace {
          type uint64;
      }
      deviate add {
          units bps;
      }
  }
  deviation /oc-ni:network-instances/oc-ni:network-instance/oc-ni:mpls/oc-ni:lsps/oc-ni:constrained-path/oc-ni:tunnels/oc-ni:tunnel/oc-ni:bandwidth/oc-ni:auto-bandwidth/oc-ni:config/oc-ni:min-bw {
      deviate replace {
          type uint64;
      }
      deviate add {
          units bps;
      }
  }
  deviation /oc-ni:network-instances/oc-ni:network-instance/oc-ni:mpls/oc-ni:lsps/oc-ni:constrained-path/oc-ni:tunnels/oc-ni:tunnel/oc-ni:bandwidth/oc-ni:auto-bandwidth/oc-ni:state/oc-ni:min-bw {
      deviate replace {
          type uint64;
      }
      deviate add {
          units bps;
      }
  }
  deviation /oc-ni:network-instances/oc-ni:network-instance/oc-ni:mpls/oc-ni:lsps/oc-ni:constrained-path/oc-ni:tunnels/oc-ni:tunnel/oc-ni:bandwidth/oc-ni:auto-bandwidth/oc-ni:config/oc-ni:adjust-interval {
      deviate replace {
          type uint32 {
              range 300..315360000;
          }
      }
      deviate add {
          units seconds;
      }
  }
  deviation /oc-ni:network-instances/oc-ni:network-instance/oc-ni:mpls/oc-ni:lsps/oc-ni:constrained-path/oc-ni:tunnels/oc-ni:tunnel/oc-ni:bandwidth/oc-ni:auto-bandwidth/oc-ni:config/oc-ni:adjust-threshold {
      deviate replace {
        type uint8 {
            range 0..50;
        }
      }
  }
  deviation /oc-ni:network-instances/oc-ni:network-instance/oc-ni:mpls/oc-ni:lsps/oc-ni:constrained-path/oc-ni:tunnels/oc-ni:tunnel/oc-ni:bandwidth/oc-ni:auto-bandwidth/oc-ni:config/oc-ni:max-bw {
      deviate replace {
          type uint64;
      }
      deviate add {
          units bps;
      }
  }
  deviation /oc-ni:network-instances/oc-ni:network-instance/oc-ni:mpls/oc-ni:lsps/oc-ni:constrained-path/oc-ni:tunnels/oc-ni:tunnel/oc-ni:bandwidth/oc-ni:auto-bandwidth/oc-ni:state/oc-ni:max-bw {
      deviate replace {
          type uint64;
      }
      deviate add {
          units bps;
      }
  }
  deviation /oc-ni:network-instances/oc-ni:network-instance/oc-ni:mpls/oc-ni:lsps/oc-ni:constrained-path/oc-ni:tunnels/oc-ni:tunnel/oc-ni:bandwidth/oc-ni:auto-bandwidth/oc-ni:overflow/oc-ni:config/oc-ni:overflow-threshold {
      deviate not-supported;
  }
  deviation /oc-ni:network-instances/oc-ni:network-instance/oc-ni:mpls/oc-ni:lsps/oc-ni:constrained-path/oc-ni:tunnels/oc-ni:tunnel/oc-ni:bandwidth/oc-ni:auto-bandwidth/oc-ni:underflow/oc-ni:config/oc-ni:underflow-threshold {
      deviate not-supported;
  }
  deviation /oc-ni:network-instances/oc-ni:network-instance/oc-ni:mpls/oc-ni:lsps/oc-ni:constrained-path/oc-ni:tunnels/oc-ni:tunnel/oc-ni:bandwidth/oc-ni:auto-bandwidth/oc-ni:state/oc-ni:interval-high-bw {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path {
      deviate add {
          max-elements 1;
      }
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:config/oc-ni:cspf-tiebreaker {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:config/oc-ni:path-computation-method {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:config/oc-ni:path-computation-server {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:config/oc-ni:explicit-path-name {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:config/oc-ni:retry-timer {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:candidate-secondary-paths {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:path-metric-bound-constraints {
      deviate not-supported;
      description "Not supported in this release.";
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:state/oc-ni:spf-metric {
      deviate not-supported;
      description "Not supported in this release.";
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:config/oc-ni:cspf-tiebreaker {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:config/oc-ni:path-computation-method {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:config/oc-ni:path-computation-server {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:config/oc-ni:explicit-path-name {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:config/oc-ni:retry-timer {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:path-metric-bound-constraints {
      deviate not-supported;
      description "Not supported in this release.";
  }
deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:state/oc-ni:spf-metric {
      deviate not-supported;
      description "Not supported in this release.";
  }

  deviation /oc-ni:network-instances/oc-ni:network-instance/oc-ni:mpls/oc-ni:lsps/oc-ni:constrained-path/oc-ni:tunnels/oc-ni:tunnel/oc-ni:state/oc-ni:counters/oc-ni:packets {
      deviate not-supported;
  }
  deviation /oc-ni:network-instances/oc-ni:network-instance/oc-ni:mpls/oc-ni:lsps/oc-ni:constrained-path/oc-ni:tunnels/oc-ni:tunnel/oc-ni:state/oc-ni:counters/oc-ni:bytes {
      deviate not-supported;
  }
  // JUNOS preference is uint32 [range 0:4294967295]
  deviation /oc-ni:network-instances/oc-ni:network-instance/oc-ni:mpls/oc-ni:lsps/oc-ni:constrained-path/oc-ni:tunnels/oc-ni:tunnel/oc-ni:state/oc-ni:preference {
      deviate replace {
          type uint32 {
              range 0..4294967295;
          }
      }
  }
  // JUNOS preference is uint32 [range 0:4294967295]
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:state/oc-ni:preference {
      deviate replace {
          type uint32 {
              range 0..4294967295;
          }
      }
  }
  // JUNOS preference is uint32 [range 0:4294967295]
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:state/oc-ni:preference {
      deviate replace {
          type uint32 {
              range 0..4294967295;
          }
      }
  }

  // Network-Instance - BGP Deviations

  // BGP Deviations

  deviation /oc-bgp:bgp {
      description
          "Junos does not support configuting bgp in openconfig-bgp directly must configure through network-instance";
      deviate not-supported;
  }

  deviation /oc-platform:components/oc-platform:component/oc-platform:state/oc-platform:used-power {
      description "Junos does not support used power for components";
      deviate not-supported;
  }

  deviation /oc-platform:components/oc-platform:component/oc-platform:state/oc-platform:temperature/oc-platform:max {
      description "Not supported in this release";
      deviate not-supported;
  }

  deviation /oc-platform:components/oc-platform:component/oc-platform:state/oc-platform:temperature/oc-platform:max-time {
      description "Not supported in this release";
      deviate not-supported;
  }

  deviation /oc-platform:components/oc-platform:component/oc-platform:state/oc-platform:temperature/oc-platform:alarm-status {
      description "Not supported in this release";
      deviate not-supported;
  }

  deviation /oc-platform:components/oc-platform:component/oc-transceiver:transceiver/oc-transceiver:config {
      description "Not supported in this release";
      deviate not-supported;
  }

  deviation /oc-platform:components/oc-platform:component/oc-transceiver:transceiver/oc-transceiver:state/oc-transceiver:fec-uncorrectable-words {
      description "Not supported in this release";
      deviate not-supported;
  }

  deviation /oc-platform:components/oc-platform:component/oc-transceiver:transceiver/oc-transceiver:state/oc-transceiver:fec-corrected-bytes {
      description "Not supported in this release";
      deviate not-supported;
  }

  deviation /oc-platform:components/oc-platform:component/oc-transceiver:transceiver/oc-transceiver:state/oc-transceiver:pre-fec-ber {
      description "Not supported in this release";
      deviate not-supported;
  }

  deviation /oc-platform:components/oc-platform:component/oc-transceiver:transceiver/oc-transceiver:state/oc-transceiver:post-fec-ber {
      description "Not supported in this release";
      deviate not-supported;
  }

  deviation /oc-platform:components/oc-platform:component/oc-transceiver:transceiver/oc-transceiver:physical-channels/oc-transceiver:channel/oc-transceiver:config {
      description "Not supported in this release";
      deviate not-supported;
  }

  deviation /oc-platform:components/oc-platform:component/oc-opt-term:optical-channel/oc-opt-term:config/oc-opt-term:line-port {
      description "Not supported in this release";
      deviate not-supported;
  }

  deviation /oc-platform:components/oc-platform:component/oc-opt-term:optical-channel/oc-opt-term:config/oc-opt-term:operational-mode {
      description "Not supported in this release";
      deviate not-supported;
  }

  deviation /oc-platform:components/oc-platform:component/oc-opt-term:optical-channel/oc-opt-term:config/oc-opt-term:target-output-power {
      description "Not supported in this release";
      deviate not-supported;
  }

  deviation /oc-platform:components/oc-platform:component/oc-opt-term:optical-channel/oc-opt-term:state/oc-opt-term:target-output-power {
      description "Not supported in this release";
      deviate not-supported;
  }

  deviation /oc-platform:components/oc-platform:component/oc-opt-term:optical-channel/oc-opt-term:state/oc-opt-term:operational-mode {
      description "Not supported in this release";
      deviate not-supported;
  }

  deviation /oc-platform:components/oc-platform:component/oc-opt-term:optical-channel/oc-opt-term:state/oc-opt-term:group-id {
      description "Not supported in this release";
      deviate not-supported;
  }

  deviation /oc-platform:components/oc-platform:component/oc-opt-term:optical-channel/oc-opt-term:state/oc-opt-term:polarization-mode-dispersion {
      description "Not supported in this release";
      deviate not-supported;
  }

  deviation /oc-platform:components/oc-platform:component/oc-opt-term:optical-channel/oc-opt-term:state/oc-opt-term:modulation-error-ratio {
      description "Not supported in this release";
      deviate not-supported;
  }

  deviation /oc-platform:components/oc-platform:component/oc-opt-term:optical-channel/oc-opt-term:state/oc-opt-term:fec-uncorrectable-blocks {
      description "Not supported in this release";
      deviate not-supported;
  }

  deviation /oc-platform:components/oc-platform:component/oc-opt-term:optical-channel/oc-opt-term:state/oc-opt-term:post-fec-ber {
      description "Not supported in this release";
      deviate not-supported;
  }

  deviation /oc-platform:components/oc-platform:component/oc-opt-term:optical-channel/oc-opt-term:state/oc-opt-term:q-value {
      description "Not supported in this release";
      deviate not-supported;
  }

  deviation /oc-opt-term:terminal-device {
      description "Not supported in this release";
      deviate not-supported;
  }

  deviation /oc-ni:network-instances/oc-ni:network-instance/oc-ni:protocols/oc-ni:protocol/oc-ni:bgp/oc-ni:global/oc-ni:default-route-distance {
      description
          "Junos does not support separate external and internal default-route-distance config knobs."; 
      deviate not-supported;
  }
  deviation /oc-ni:network-instances/oc-ni:network-instance/oc-ni:protocols/oc-ni:protocol/oc-ni:bgp/oc-ni:global/oc-ni:use-multiple-paths {
      description 
          "There is no protocol level config knob for this in Junos.";
      deviate not-supported;
  }
 deviation /oc-ni:network-instances/oc-ni:network-instance/oc-ni:protocols/oc-ni:protocol/oc-ni:bgp/oc-ni:global/oc-ni:afi-safis/oc-ni:afi-safi/oc-ni:route-selection-options/oc-ni:config/oc-ni:advertise-inactive-routes {
      description 
          "In Junos, -advertise-inactive-routes- can not be set per address
           family.";
      deviate not-supported;
  }
  deviation /oc-ni:network-instances/oc-ni:network-instance/oc-ni:protocols/oc-ni:protocol/oc-ni:bgp/oc-ni:global/oc-ni:afi-safis/oc-ni:afi-safi/oc-ni:route-selection-options/oc-ni:config/oc-ni:always-compare-med {
      description 
          "In Junos, -always-compare-med- can not be set per address family.";
      deviate not-supported;
  }
  deviation /oc-ni:network-instances/oc-ni:network-instance/oc-ni:protocols/oc-ni:protocol/oc-ni:bgp/oc-ni:global/oc-ni:afi-safis/oc-ni:afi-safi/oc-ni:route-selection-options/oc-ni:config/oc-ni:external-compare-router-id {
      description 
          "In Junos, -external-compare-router-id- can not be set per address
           family.";
      deviate not-supported;
  }
  deviation /oc-ni:network-instances/oc-ni:network-instance/oc-ni:protocols/oc-ni:protocol/oc-ni:bgp/oc-ni:global/oc-ni:afi-safis/oc-ni:afi-safi/oc-ni:route-selection-options/oc-ni:config/oc-ni:ignore-as-path-length {
      description 
          "In Junos, -ignore-as-path-length- can not be set per address 
           family.";
      deviate not-supported;
  }
  deviation /oc-ni:network-instances/oc-ni:network-instance/oc-ni:protocols/oc-ni:protocol/oc-ni:bgp/oc-ni:global/oc-ni:afi-safis/oc-ni:afi-safi/oc-ni:route-selection-options/oc-ni:config/oc-ni:ignore-next-hop-igp-metric {
      description 
          "There is no BGP specific config knob for this in Junos.";
      deviate not-supported;
  }
  deviation /oc-ni:network-instances/oc-ni:network-instance/oc-ni:protocols/oc-ni:protocol/oc-ni:bgp/oc-ni:global/oc-ni:afi-safis/oc-ni:afi-safi/oc-ni:use-multiple-paths {
      description 
          "In Junos, -multipath- config cannot be set per address family.";
      deviate not-supported;
  }
  deviation /oc-ni:network-instances/oc-ni:network-instance/oc-ni:protocols/oc-ni:protocol/oc-ni:bgp/oc-ni:global/oc-ni:afi-safis/oc-ni:afi-safi/oc-ni:ipv4-unicast/oc-ni:config/oc-ni:send-default-route {
      description 
          "There is no BGP specific config knob for this in Junos.";
      deviate not-supported;
  }
  deviation /oc-ni:network-instances/oc-ni:network-instance/oc-ni:protocols/oc-ni:protocol/oc-ni:bgp/oc-ni:global/oc-ni:afi-safis/oc-ni:afi-safi/oc-ni:ipv6-unicast/oc-ni:config/oc-ni:send-default-route {
      description 
          "There is no BGP specific config knob for this in Junos.";
      deviate not-supported;
  }
 deviation /oc-ni:network-instances/oc-ni:network-instance/oc-ni:protocols/oc-ni:protocol/oc-ni:bgp/oc-ni:peer-groups/oc-ni:peer-group/oc-ni:config/oc-ni:send-community {
      description 
          "There is no BGP specific config knob for this in Junos.";
      deviate not-supported;
  }
  deviation /oc-ni:network-instances/oc-ni:network-instance/oc-ni:protocols/oc-ni:protocol/oc-ni:bgp/oc-ni:peer-groups/oc-ni:peer-group/oc-ni:timers/oc-ni:config/oc-ni:keepalive-interval {
      description 
          "In Junos, the keepalive-interval is always 1/3 hold-time.";
      deviate not-supported;
  }
  deviation /oc-ni:network-instances/oc-ni:network-instance/oc-ni:protocols/oc-ni:protocol/oc-ni:bgp/oc-ni:peer-groups/oc-ni:peer-group/oc-ni:as-path-options/oc-ni:config/oc-ni:disable-peer-as-filter {
      description
          "There is no BGP specific config knob at the peer-group level for this in Junos.";
      deviate not-supported;
  }
  deviation /oc-ni:network-instances/oc-ni:network-instance/oc-ni:protocols/oc-ni:protocol/oc-ni:bgp/oc-ni:peer-groups/oc-ni:peer-group/oc-ni:afi-safis/oc-ni:afi-safi/oc-ni:add-paths/oc-ni:config/oc-ni:send-max {
      deviate replace {
          type uint8 {
              range 2..6;
          }
      }  
   }
  deviation /oc-ni:network-instances/oc-ni:network-instance/oc-ni:protocols/oc-ni:protocol/oc-ni:bgp/oc-ni:peer-groups/oc-ni:peer-group/oc-ni:afi-safis/oc-ni:afi-safi/oc-ni:add-paths/oc-ni:config/oc-ni:send {
      deviate add {
          must '(. = "false" or send-max)' {
           error-message
             "When 'send' is true, send-max must be configured.";
          }
      }  
   }
  deviation /oc-ni:network-instances/oc-ni:network-instance/oc-ni:protocols/oc-ni:protocol/oc-ni:bgp/oc-ni:peer-groups/oc-ni:peer-group/oc-ni:afi-safis/oc-ni:afi-safi/oc-ni:use-multiple-paths {
      description 
          "In Junos, -multipath- config cannot be set per address family.";
      deviate not-supported;
  }
  deviation /oc-ni:network-instances/oc-ni:network-instance/oc-ni:protocols/oc-ni:protocol/oc-ni:bgp/oc-ni:peer-groups/oc-ni:peer-group/oc-ni:afi-safis/oc-ni:afi-safi/oc-ni:apply-policy {
      description 
          "In Junos, import/export policies cannot be applied per address 
           family.";
      deviate not-supported;
  }
  deviation /oc-ni:network-instances/oc-ni:network-instance/oc-ni:protocols/oc-ni:protocol/oc-ni:bgp/oc-ni:peer-groups/oc-ni:peer-group/oc-ni:afi-safis/oc-ni:afi-safi/oc-ni:ipv4-unicast/oc-ni:prefix-limit/oc-ni:config/oc-ni:prevent-teardown {
      deviate add {
          must '(. = "true" or max-prefix)' {
           error-message
             "When 'prevent-teardown' is true, max-prefix must be configured.";
          }
      }  
   }
  deviation /oc-ni:network-instances/oc-ni:network-instance/oc-ni:protocols/oc-ni:protocol/oc-ni:bgp/oc-ni:peer-groups/oc-ni:peer-group/oc-ni:afi-safis/oc-ni:afi-safi/oc-ni:ipv4-unicast/oc-ni:config/oc-ni:send-default-route {
      description 
          "There is no BGP specific config knob for this in Junos.";
      deviate not-supported;
  }
  deviation /oc-ni:network-instances/oc-ni:network-instance/oc-ni:protocols/oc-ni:protocol/oc-ni:bgp/oc-ni:peer-groups/oc-ni:peer-group/oc-ni:apply-policy/oc-ni:config/oc-ni:default-import-policy {
      description 
          "In Junos, the default-policy is the one at the end of the 
           policy-chain.";
      deviate not-supported;
  }
  deviation /oc-ni:network-instances/oc-ni:network-instance/oc-ni:protocols/oc-ni:protocol/oc-ni:bgp/oc-ni:peer-groups/oc-ni:peer-group/oc-ni:apply-policy/oc-ni:config/oc-ni:default-export-policy {
      description 
          "In Junos, the default-policy is the one at the end of the 
           policy-chain.";
      deviate not-supported;
  }
  deviation /oc-ni:network-instances/oc-ni:network-instance/oc-ni:protocols/oc-ni:protocol/oc-ni:bgp/oc-ni:peer-groups/oc-ni:peer-group/oc-ni:afi-safis/oc-ni:afi-safi/oc-ni:ipv6-unicast/oc-ni:config/oc-ni:send-default-route {
      description 
          "There is no BGP specific config knob for this in Junos.";
      deviate not-supported;
  }
  deviation /oc-ni:network-instances/oc-ni:network-instance/oc-ni:protocols/oc-ni:protocol/oc-ni:bgp/oc-ni:neighbors/oc-ni:neighbor/oc-ni:config/oc-ni:neighbor-address {
      deviate replace {
          type inet:ip-address;
      }
  }
  deviation /oc-ni:network-instances/oc-ni:network-instance/oc-ni:protocols/oc-ni:protocol/oc-ni:bgp/oc-ni:neighbors/oc-ni:neighbor/oc-ni:transport/oc-ni:state/oc-ni:remote-address {
      deviate replace {
          type inet:ip-address;
      }
  }
  deviation /oc-ni:network-instances/oc-ni:network-instance/oc-ni:protocols/oc-ni:protocol/oc-ni:bgp/oc-ni:neighbors/oc-ni:neighbor/oc-ni:config/oc-ni:send-community {
      description 
          "There is no BGP specific config knob for this in Junos.";
      deviate not-supported;
  }
  deviation /oc-ni:network-instances/oc-ni:network-instance/oc-ni:protocols/oc-ni:protocol/oc-ni:bgp/oc-ni:neighbors/oc-ni:neighbor/oc-ni:timers/oc-ni:config/oc-ni:keepalive-interval {
      description 
          "In Junos, the keepalive-interval is always 1/3 hold-time.";
      deviate not-supported;
  }
  deviation /oc-ni:network-instances/oc-ni:network-instance/oc-ni:protocols/oc-ni:protocol/oc-ni:bgp/oc-ni:neighbors/oc-ni:neighbor/oc-ni:afi-safis/oc-ni:afi-safi/oc-ni:add-paths/oc-ni:config/oc-ni:send-max {
      deviate replace {
          type uint8 {
              range 2..6;
          }
      }  
   }
  deviation /oc-ni:network-instances/oc-ni:network-instance/oc-ni:protocols/oc-ni:protocol/oc-ni:bgp/oc-ni:neighbors/oc-ni:neighbor/oc-ni:afi-safis/oc-ni:afi-safi/oc-ni:add-paths/oc-ni:config/oc-ni:send {
      deviate add {
           must '(. = "false" or ../send-max )' {
           error-message
             "When 'send' is true, send-max must be configured.";
          }
      }  
   }
  deviation /oc-ni:network-instances/oc-ni:network-instance/oc-ni:protocols/oc-ni:protocol/oc-ni:bgp/oc-ni:neighbors/oc-ni:neighbor/oc-ni:afi-safis/oc-ni:afi-safi/oc-ni:use-multiple-paths {
      description 
          "In Junos, -multipath- config cannot be set per address family.";
      deviate not-supported;
  }
  deviation /oc-ni:network-instances/oc-ni:network-instance/oc-ni:protocols/oc-ni:protocol/oc-ni:bgp/oc-ni:neighbors/oc-ni:neighbor/oc-ni:afi-safis/oc-ni:afi-safi/oc-ni:apply-policy {
      description 
          "In Junos, import/export policies cannot be applied per address 
           family.";
      deviate not-supported;
  }
  deviation /oc-ni:network-instances/oc-ni:network-instance/oc-ni:protocols/oc-ni:protocol/oc-ni:bgp/oc-ni:neighbors/oc-ni:neighbor/oc-ni:afi-safis/oc-ni:afi-safi/oc-ni:ipv4-unicast/oc-ni:prefix-limit/oc-ni:config/oc-ni:prevent-teardown {
      deviate add {
          must '(. = "true" or max-prefix)' {
           error-message
             "When 'prevent-teardown' is true, max-prefix must be configured.";
          }
      }  
   }
  deviation /oc-ni:network-instances/oc-ni:network-instance/oc-ni:protocols/oc-ni:protocol/oc-ni:bgp/oc-ni:neighbors/oc-ni:neighbor/oc-ni:afi-safis/oc-ni:afi-safi/oc-ni:ipv6-unicast/oc-ni:prefix-limit/oc-ni:config/oc-ni:prevent-teardown {
      deviate add {
          must '(. = "true" or max-prefix)' {
           error-message
             "When 'prevent-teardown' is true, max-prefix must be configured.";
          }
      }  
   }
  deviation /oc-ni:network-instances/oc-ni:network-instance/oc-ni:protocols/oc-ni:protocol/oc-ni:bgp/oc-ni:neighbors/oc-ni:neighbor/oc-ni:afi-safis/oc-ni:afi-safi/oc-ni:ipv4-unicast/oc-ni:config/oc-ni:send-default-route {
      description 
          "There is no BGP specific config knob for this in Junos.";
      deviate not-supported;
  }
  deviation /oc-ni:network-instances/oc-ni:network-instance/oc-ni:protocols/oc-ni:protocol/oc-ni:bgp/oc-ni:neighbors/oc-ni:neighbor/oc-ni:afi-safis/oc-ni:afi-safi/oc-ni:ipv6-unicast/oc-ni:config/oc-ni:send-default-route {
      description 
          "There is no BGP specific config knob for this in Junos.";
      deviate not-supported;
  }
  deviation /oc-ni:network-instances/oc-ni:network-instance/oc-ni:protocols/oc-ni:protocol/oc-ni:bgp/oc-ni:neighbors/oc-ni:neighbor/oc-ni:apply-policy/oc-ni:config/oc-ni:default-import-policy {
      description 
          "In Junos, the default-policy is the one at the end of the 
           policy-chain.";
      deviate not-supported;
  }
  deviation /oc-ni:network-instances/oc-ni:network-instance/oc-ni:protocols/oc-ni:protocol/oc-ni:bgp/oc-ni:neighbors/oc-ni:neighbor/oc-ni:apply-policy/oc-ni:config/oc-ni:default-export-policy {
      description 
          "In Junos, the default-policy is the one at the end of the 
           policy-chain.";
      deviate not-supported;
  }
  deviation /oc-ni:network-instances/oc-ni:network-instance/oc-ni:protocols/oc-ni:protocol/oc-ni:bgp/oc-ni:global/oc-ni:config/oc-ni:router-id {
      deviate replace {
          type yang:dotted-quad;
      }
  }
  deviation /oc-ni:network-instances/oc-ni:network-instance/oc-ni:protocols/oc-ni:protocol/oc-ni:bgp/oc-ni:global/oc-ni:afi-safis/oc-ni:afi-safi/oc-ni:route-selection-options/oc-ni:state/oc-ni:enable-aigp {
      description
          "In Junos, -enable-aigp- is supported only for labeled-unicast.";
      deviate not-supported;
  }
  deviation /oc-ni:network-instances/oc-ni:network-instance/oc-ni:protocols/oc-ni:protocol/oc-ni:bgp/oc-ni:global/oc-ni:afi-safis/oc-ni:afi-safi/oc-ni:route-selection-options/oc-ni:state/oc-ni:ignore-next-hop-igp-metric {
      description
          "There is no BGP specific state for this in Junos.";
      deviate not-supported;
  }
  deviation /oc-ni:network-instances/oc-ni:network-instance/oc-ni:protocols/oc-ni:protocol/oc-ni:bgp/oc-ni:global/oc-ni:afi-safis/oc-ni:afi-safi/oc-ni:ipv4-unicast/oc-ni:state/oc-ni:send-default-route {
      description
          "There is no BGP specific state for this in Junos.";
      deviate not-supported;
  }
  deviation /oc-ni:network-instances/oc-ni:network-instance/oc-ni:protocols/oc-ni:protocol/oc-ni:bgp/oc-ni:global/oc-ni:afi-safis/oc-ni:afi-safi/oc-ni:ipv6-unicast/oc-ni:state/oc-ni:send-default-route {
      description
          "There is no BGP specific state for this in Junos.";
      deviate not-supported;
  }
  deviation /oc-ni:network-instances/oc-ni:network-instance/oc-ni:protocols/oc-ni:protocol/oc-ni:bgp/oc-ni:global/oc-ni:dynamic-neighbor-prefixes/oc-ni:dynamic-neighbor-prefix {
      description
          "Junos supports dynamic-neighbors at peer-group level, not in global.";
      deviate not-supported;
  }
  deviation /oc-ni:network-instances/oc-ni:network-instance/oc-ni:protocols/oc-ni:protocol/oc-ni:bgp/oc-ni:neighbors/oc-ni:neighbor/oc-ni:afi-safis/oc-ni:afi-safi/oc-ni:ipv4-unicast/oc-ni:state/oc-ni:send-default-route {
      description
          "There is no BGP specific state for this in Junos.";
      deviate not-supported;
  }
  deviation /oc-ni:network-instances/oc-ni:network-instance/oc-ni:protocols/oc-ni:protocol/oc-ni:bgp/oc-ni:neighbors/oc-ni:neighbor/oc-ni:afi-safis/oc-ni:afi-safi/oc-ni:ipv6-unicast/oc-ni:state/oc-ni:send-default-route {
      description
          "There is no BGP specific state for this in Junos.";
      deviate not-supported;
  }
  deviation /oc-ni:network-instances/oc-ni:network-instance/oc-ni:protocols/oc-ni:protocol/oc-ni:bgp/oc-ni:peer-groups/oc-ni:peer-group/oc-ni:afi-safis/oc-ni:afi-safi/oc-ni:ipv4-unicast/oc-ni:state/oc-ni:send-default-route {
      description
          "There is no BGP specific state for this in Junos.";
      deviate not-supported;
  }
  deviation /oc-ni:network-instances/oc-ni:network-instance/oc-ni:protocols/oc-ni:protocol/oc-ni:bgp/oc-ni:peer-groups/oc-ni:peer-group/oc-ni:afi-safis/oc-ni:afi-safi/oc-ni:ipv6-unicast/oc-ni:state/oc-ni:send-default-route {
      description
          "There is no BGP specific state for this in Junos.";
      deviate not-supported;
  }

  // openconfig-system deviations
  deviation /oc-system:system/oc-system:state {
      deviate not-supported;
  }
  deviation /oc-system:system/oc-sys-grpc:grpc-servers/oc-sys-grpc:grpc-server/oc-sys-grpc:config/oc-sys-grpc:listen-addresses {
      deviate add {
          max-elements 1;
      }
  }
  deviation /oc-system:system/oc-system:ntp/oc-system:config/oc-system:ntp-source-address {
      deviate not-supported;
  }
  deviation /oc-system:system/oc-system:ntp/oc-system:config/oc-system:enable-ntp-auth {
      deviate not-supported;
  }
  deviation /oc-system:system/oc-system:ntp/oc-system:ntp-keys {
      deviate not-supported;
  }
  deviation /oc-system:system/oc-system:ntp/oc-system:servers/oc-system:server/oc-system:config/oc-system:port {
      deviate not-supported;
  }
  deviation /oc-system:system/oc-system:ntp/oc-system:servers/oc-system:server/oc-system:config/oc-system:association-type {
       deviate not-supported;
  }
  deviation /oc-system:system/oc-system:ntp/oc-system:servers/oc-system:server/oc-system:config/oc-system:iburst {
      deviate not-supported;
  }
  deviation /oc-system:system/oc-system:ntp/oc-system:servers/oc-system:server/oc-system:config/oc-system:address {
      deviate not-supported;
  }
  deviation /oc-system:system/oc-sys-grpc:grpc-servers/oc-sys-grpc:grpc-server/oc-sys-grpc:config/oc-sys-grpc:metadata-authentication {
      deviate not-supported;
  }
  deviation /oc-system:system/oc-system:dns/oc-system:servers {
      deviate not-supported;
  }
  deviation /oc-system:system/oc-system:dns/oc-system:config/oc-system:search {
      deviate add {
          max-elements 6;
      }
  }
  deviation /oc-system:system/oc-system:dns/oc-system:host-entries {
      deviate not-supported;
  }
  deviation /oc-system:system/oc-system:telnet-server/oc-system:config/oc-system:timeout {
      deviate not-supported;
  }
  deviation /oc-system:system/oc-system:memory {
      deviate not-supported;
  }
  deviation /oc-system:system/oc-system:processes {
      deviate not-supported;
  }
  deviation /oc-system:system/oc-system:aaa/oc-system:config {
      deviate not-supported;
  }
  deviation /oc-system:system/oc-system:aaa/oc-system:authorization/oc-system:config {
      deviate not-supported;
  }
  deviation /oc-system:system/oc-system:aaa/oc-system:authorization/oc-system:events {
      deviate not-supported;
  }
  deviation /oc-system:system/oc-system:aaa/oc-system:accounting/oc-system:events/oc-system:event/oc-system:config/oc-system:record {
        deviate not-supported;
  }
  deviation /oc-system:system/oc-system:aaa/oc-system:authentication/oc-system:users/oc-system:user/oc-system:config/oc-system:ssh-key {
      deviate not-supported;
  }
  deviation /oc-system:system/oc-system:aaa/oc-system:server-groups/oc-system:server-group/oc-system:servers/oc-system:server/oc-system:radius/oc-system:config/oc-system:source-address {
      deviate replace {
          type inet:ip-address;
      }
  }
  deviation /oc-system:system/oc-system:aaa/oc-system:server-groups/oc-system:server-group/oc-system:servers/oc-system:server/oc-system:tacacs/oc-system:config/oc-system:source-address {
      deviate replace {
          type inet:ip-address;
      }
  }
  deviation /oc-system:system/oc-system:aaa/oc-system:server-groups/oc-system:server-group/oc-system:servers/oc-system:server/oc-system:config/oc-system:address {
      deviate replace {
          type inet:ip-address;
      }
  }
deviation /oc-system:system/oc-system:aaa/oc-system:server-groups/oc-system:server-group/oc-system:servers/oc-system:server/oc-system:tacacs/oc-system:config/oc-system:secret-key-hashed {
	deviate not-supported;
}

deviation /oc-system:system/oc-system:aaa/oc-system:server-groups/oc-system:server-group/oc-system:servers/oc-system:server/oc-system:radius/oc-system:config/oc-system:secret-key-hashed {
        deviate not-supported;
}
  // openconfig-lacp deviations
  deviation /oc-lacp:lacp/oc-lacp:interfaces/oc-lacp:interface/oc-lacp:config/oc-lacp:system-id-mac {
      deviate replace {
          type yang:mac-address;
      }
  }

  deviation /oc-if:interfaces/oc-if:interface/oc-eth:ethernet/oc-eth:state/oc-eth:hw-mac-address {
      deviate replace {
          type yang:mac-address;
      }
  }

  deviation /oc-if:interfaces/oc-if:interface/oc-eth:ethernet/oc-eth:config/oc-eth:mac-address {
      deviate replace {
          type yang:mac-address;
      }
  }
  
  deviation /oc-bfd:bfd/oc-bfd:interfaces/oc-bfd:interface/oc-bfd:micro-bfd-sessions/oc-bfd:micro-bfd-session/oc-bfd:config/oc-bfd:local-address {
      deviate replace {
          type inet:ip-address;
      }
  }
  deviation /oc-bfd:bfd/oc-bfd:interfaces/oc-bfd:interface/oc-bfd:micro-bfd-sessions/oc-bfd:micro-bfd-session/oc-bfd:config/oc-bfd:remote-address {
      deviate replace {
          type inet:ip-address;
      }
  }
  // JUNOS preference BFD timer configs in milliseconds.
  deviation /oc-bfd:bfd/oc-bfd:interfaces/oc-bfd:interface/oc-bfd:config/oc-bfd:desired-minimum-tx-interval {
      deviate replace {
	  units milliseconds;
      }
  }
  deviation /oc-bfd:bfd/oc-bfd:interfaces/oc-bfd:interface/oc-bfd:config/oc-bfd:required-minimum-receive {
      deviate replace {
          units milliseconds;
      }
   }
  deviation /oc-bfd:bfd/oc-bfd:interfaces/oc-bfd:interface/oc-bfd:config/oc-bfd:enabled {
    description
      "Junos does not support BFD configuration on member interface";
    deviate not-supported;
   }
  deviation /oc-bfd:bfd/oc-bfd:interfaces/oc-bfd:interface/oc-bfd:config/oc-bfd:id {
    description
      "Junos does not support BFD member id config";
    deviate not-supported;
   }
  deviation /oc-bfd:bfd/oc-bfd:interfaces/oc-bfd:interface/oc-bfd:config/oc-bfd:local-address {
    description
      "Junos does not support BFD member-link local-address config";
    deviate not-supported;
   }
  deviation /oc-bfd:bfd/oc-bfd:interfaces/oc-bfd:interface/oc-bfd:micro-bfd-sessions/oc-bfd:micro-bfd-session/oc-bfd:config/oc-bfd:member-interface {
    description
      "Junos does not support BFD individual AE member interface config";
    deviate not-supported;
   }
  deviation /oc-bfd:bfd/oc-bfd:interfaces/oc-bfd:interface/oc-bfd:interface-ref{
    description
      "Junos does not support interface-ref config";
    deviate not-supported;
   }

    deviation /oc-bfd:bfd/oc-bfd:interfaces/oc-bfd:interface/oc-bfd:micro-bfd-sessions/oc-bfd:micro-bfd-session/oc-bfd:state/oc-bfd:async/oc-bfd:last-packet-transmitted {
	description
	    "Junos does not support per bfd session stats";
	deviate not-supported;
    }
    deviation /oc-bfd:bfd/oc-bfd:interfaces/oc-bfd:interface/oc-bfd:micro-bfd-sessions/oc-bfd:micro-bfd-session/oc-bfd:state/oc-bfd:async/oc-bfd:last-packet-received {
	description
	    "Junos does not support per bfd session stats";
	deviate not-supported;
    }
    deviation /oc-bfd:bfd/oc-bfd:interfaces/oc-bfd:interface/oc-bfd:micro-bfd-sessions/oc-bfd:micro-bfd-session/oc-bfd:state/oc-bfd:async/oc-bfd:transmitted-packets {
	description
	    "Junos does not support per bfd session stats";
	deviate not-supported;
    }
    deviation /oc-bfd:bfd/oc-bfd:interfaces/oc-bfd:interface/oc-bfd:micro-bfd-sessions/oc-bfd:micro-bfd-session/oc-bfd:state/oc-bfd:async/oc-bfd:received-packets {
	description
	    "Junos does not support per bfd session stats";
	deviate not-supported;
    }
    deviation /oc-bfd:bfd/oc-bfd:interfaces/oc-bfd:interface/oc-bfd:micro-bfd-sessions/oc-bfd:micro-bfd-session/oc-bfd:state/oc-bfd:async/oc-bfd:up-transitions {
	description
	    "Junos does not support per bfd session stats";
	deviate not-supported;
    }
    deviation /oc-bfd:bfd/oc-bfd:interfaces/oc-bfd:interface/oc-bfd:peers/oc-bfd:peer/oc-bfd:state/oc-bfd:echo/oc-bfd:last-packet-transmitted {
	description
	    "Junos does not support per bfd session stats";
	deviate not-supported;
    }
    deviation /oc-bfd:bfd/oc-bfd:interfaces/oc-bfd:interface/oc-bfd:peers/oc-bfd:peer/oc-bfd:state/oc-bfd:echo/oc-bfd:last-packet-received {
	description
	    "Junos does not support per bfd session stats";
	deviate not-supported;
    }
    deviation /oc-bfd:bfd/oc-bfd:interfaces/oc-bfd:interface/oc-bfd:peers/oc-bfd:peer/oc-bfd:state/oc-bfd:echo/oc-bfd:transmitted-packets {
	description
	    "Junos does not support per bfd session stats";
	deviate not-supported;
    }
    deviation /oc-bfd:bfd/oc-bfd:interfaces/oc-bfd:interface/oc-bfd:peers/oc-bfd:peer/oc-bfd:state/oc-bfd:echo/oc-bfd:received-packets {
	description
	    "Junos does not support per bfd session stats";
	deviate not-supported;
    }
    deviation /oc-bfd:bfd/oc-bfd:interfaces/oc-bfd:interface/oc-bfd:peers/oc-bfd:peer/oc-bfd:state/oc-bfd:echo/oc-bfd:up-transitions {
	description
	    "Junos does not support per bfd session stats";
	deviate not-supported;
    }
    deviation /oc-bfd:bfd/oc-bfd:interfaces/oc-bfd:interface/oc-bfd:peers/oc-bfd:peer/oc-bfd:state/oc-bfd:async/oc-bfd:last-packet-transmitted {
	description
	    "Junos does not support per bfd session stats";
	deviate not-supported;
    }
    deviation /oc-bfd:bfd/oc-bfd:interfaces/oc-bfd:interface/oc-bfd:peers/oc-bfd:peer/oc-bfd:state/oc-bfd:async/oc-bfd:last-packet-received {
	description
	    "Junos does not support per bfd session stats";
	deviate not-supported;
    }
    deviation /oc-bfd:bfd/oc-bfd:interfaces/oc-bfd:interface/oc-bfd:peers/oc-bfd:peer/oc-bfd:state/oc-bfd:async/oc-bfd:transmitted-packets {
	description
	    "Junos does not support per bfd session stats";
	deviate not-supported;
    }
    deviation /oc-bfd:bfd/oc-bfd:interfaces/oc-bfd:interface/oc-bfd:peers/oc-bfd:peer/oc-bfd:state/oc-bfd:async/oc-bfd:received-packets {
	description
	    "Junos does not support per bfd session stats";
	deviate not-supported;
    }
    deviation /oc-bfd:bfd/oc-bfd:interfaces/oc-bfd:interface/oc-bfd:peers/oc-bfd:peer/oc-bfd:state/oc-bfd:async/oc-bfd:up-transitions {
	description
	    "Junos does not support per bfd session stats";
	deviate not-supported;
    }
  deviation /oc-bfd:bfd/oc-bfd:interfaces/oc-bfd:interface/oc-bfd:peers {
    description
      "Junos does not support peers config";
    deviate not-supported;
   }
  deviation /oc-if:interfaces/oc-if:interface/oc-eth:ethernet/oc-eth:state/oc-eth:duplex-mode {
      deviate replace {
          type enumeration {
              enum HALF {
                  description "Full duplex mode";
              }
              enum FULL {
                  description "Half duplex mode";
              }
              enum NOT-NEGOTIATED {
                  description "Duplex mode not negotiated yet";
              }
          }
      }
  }
  deviation /oc-if:interfaces/oc-if:interface/oc-eth:ethernet/oc-eth:state/oc-eth:negotiated-duplex-mode {
      deviate replace {
          type enumeration {
              enum HALF {
                  description "Full duplex mode";
              }
              enum FULL {
                  description "Half duplex mode";
              }
              enum NOT-NEGOTIATED {
                  description "Duplex mode not negotiated yet";
              }
          }
      }
  }

  deviation /oc-platform:components/oc-platform:component/oc-platform:state/oc-platform:type {
      deviate replace {
          type string;
      }
  }
  deviation /oc-platform:components/oc-platform:component/oc-transceiver:transceiver/oc-transceiver:state/oc-transceiver:date-code {
      deviate replace {
          type string;
      }
  }
  deviation /oc-platform:components/oc-platform:component/oc-transceiver:transceiver/oc-transceiver:state/oc-transceiver:ethernet-pmd {
      deviate replace {
          type string;
      }
  }
  deviation /oc-platform:components/oc-platform:component/oc-transceiver:transceiver/oc-transceiver:state/oc-transceiver:ethernet-pmd-preconf {
      deviate replace {
          type string;
      }
  }
  deviation /oc-platform:components/oc-platform:component/oc-transceiver:transceiver/oc-transceiver:state/oc-transceiver:form-factor {
      deviate replace {
          type string;
      }
  }
  deviation /oc-platform:components/oc-platform:component/oc-transceiver:transceiver/oc-transceiver:state/oc-transceiver:form-factor-preconf {
      deviate replace {
          type string;
      }
  }
  deviation /oc-platform:components/oc-platform:component/oc-transceiver:transceiver/oc-transceiver:state/oc-transceiver:sonet-sdh-compliance-code {
      deviate replace {
          type string;
      }
  }
  deviation /oc-platform:components/oc-platform:component/oc-transceiver:transceiver/oc-transceiver:state/oc-transceiver:otn-compliance-code {
      deviate replace {
          type string;
      }
  }
  deviation /oc-platform:components/oc-platform:component/oc-transceiver:transceiver/oc-transceiver:state/oc-transceiver:vendor-rev {
      deviate replace {
          type string {
              length 1..10;
          }
      }
  }

  deviation "/oc-acl:acl/oc-acl:acl-sets/oc-acl:acl-set/oc-acl:acl-entries/oc-acl:acl-entry/oc-acl:ipv6/oc-acl:config/oc-acl:source-address"{
        deviate replace {
           type inet:ipv6-prefix;
        }
  }

  deviation "/oc-acl:acl/oc-acl:acl-sets/oc-acl:acl-set/oc-acl:acl-entries/oc-acl:acl-entry/oc-acl:ipv6/oc-acl:config/oc-acl:destination-address"{
        deviate replace {
           type inet:ipv6-prefix;
        }
  }

  deviation "/oc-acl:acl/oc-acl:acl-sets/oc-acl:acl-set/oc-acl:acl-entries/oc-acl:acl-entry/oc-acl:ipv6/oc-acl:config/oc-acl:dscp"{
        deviate replace {
           type string;
        }
  }

  deviation "/oc-acl:acl/oc-acl:acl-sets/oc-acl:acl-set/oc-acl:acl-entries/oc-acl:acl-entry/oc-acl:ipv4/oc-acl:config/oc-acl:dscp"{
        deviate replace {
           type string;
        }
  }

  deviation "/oc-acl:acl/oc-acl:acl-sets/oc-acl:acl-set/oc-acl:acl-entries/oc-acl:acl-entry/oc-acl:l2/oc-acl:config/oc-acl:destination-mac"{
        deviate replace {
           type jnx-types:mac-address-prefix;
        }
  }

  deviation "/oc-acl:acl/oc-acl:acl-sets/oc-acl:acl-set/oc-acl:acl-entries/oc-acl:acl-entry/oc-acl:l2/oc-acl:config/oc-acl:destination-mac-mask"{
        deviate not-supported;
  }

 deviation "/oc-acl:acl/oc-acl:acl-sets/oc-acl:acl-set/oc-acl:acl-entries/oc-acl:acl-entry/oc-acl:ipv6/oc-acl:config/oc-acl:destination-flow-label"{
        deviate not-supported;
  }

  deviation "/oc-acl:acl/oc-acl:acl-sets/oc-acl:acl-set/oc-acl:acl-entries/oc-acl:acl-entry/oc-acl:ipv6/oc-acl:config/oc-acl:source-flow-label"{
        deviate not-supported;
  }

  deviation "/oc-acl:acl/oc-acl:acl-sets/oc-acl:acl-set/oc-acl:acl-entries/oc-acl:acl-entry/oc-acl:l2/oc-acl:config/oc-acl:source-mac"{
        deviate replace {
           type jnx-types:mac-address-prefix;
        }
  }

  deviation "/oc-acl:acl/oc-acl:acl-sets/oc-acl:acl-set/oc-acl:acl-entries/oc-acl:acl-entry/oc-acl:l2/oc-acl:config/oc-acl:source-mac-mask"{
        deviate not-supported;
  }

deviation "/oc-acl:acl/oc-acl:acl-sets/oc-acl:acl-set/oc-acl:acl-entries/oc-acl:acl-entry/oc-acl:actions/oc-acl:config/oc-acl:forwarding-action"{
        deviate replace {
           mandatory false;
        }
  }

  deviation "/oc-acl:acl/oc-acl:interfaces/oc-acl:interface/oc-acl:interface-ref/oc-acl:config/oc-acl:interface"{
        deviate add {
           mandatory true;
        }
  }

  deviation "/oc-acl:acl/oc-acl:interfaces/oc-acl:interface/oc-acl:interface-ref/oc-acl:config/oc-acl:subinterface"{
        deviate add {
           mandatory true;
        }
  }

  deviation "/oc-acl:acl/oc-acl:acl-sets/oc-acl:acl-set/oc-acl:acl-entries/oc-acl:acl-entry/oc-acl:input-interface/oc-acl:interface-ref/oc-acl:config/oc-acl:interface"{
        deviate add {
           mandatory true;
        }
  }


  deviation "/oc-acl:acl/oc-acl:acl-sets/oc-acl:acl-set/oc-acl:acl-entries/oc-acl:acl-entry/oc-acl:input-interface/oc-acl:interface-ref/oc-acl:config/oc-acl:subinterface"{
        deviate add {
           mandatory true;
        }
  }

  deviation "/oc-acl:acl/oc-acl:acl-sets/oc-acl:acl-set/oc-acl:acl-entries/oc-acl:acl-entry/oc-acl:transport/oc-acl:config/oc-acl:destination-port"{
        deviate replace {
           type union {
               type inet:port-number;
               type jnx-types:port-range;
           }
        }
  }

  deviation "/oc-acl:acl/oc-acl:acl-sets/oc-acl:acl-set/oc-acl:acl-entries/oc-acl:acl-entry/oc-acl:transport/oc-acl:config/oc-acl:source-port"{
        deviate replace {
           type union {
               type inet:port-number;
               type jnx-types:port-range;
           }
        }
  }
 
  /* OC ACL states are not supported */
  deviation "/oc-acl:acl/oc-acl:state" {
      deviate not-supported;
  }

  deviation "/oc-acl:acl/oc-acl:acl-sets/oc-acl:acl-set/oc-acl:state" {
     deviate not-supported;
  }
 
  deviation "/oc-acl:acl/oc-acl:acl-sets/oc-acl:acl-set/oc-acl:acl-entries/oc-acl:acl-entry/oc-acl:state" {
     deviate not-supported;
  }

  deviation "/oc-acl:acl/oc-acl:acl-sets/oc-acl:acl-set/oc-acl:acl-entries/oc-acl:acl-entry/oc-acl:l2/oc-acl:state"  {
     deviate not-supported;
  }

  deviation "/oc-acl:acl/oc-acl:acl-sets/oc-acl:acl-set/oc-acl:acl-entries/oc-acl:acl-entry/oc-acl:ipv4/oc-acl:state"  {  
     deviate not-supported;
  }

   deviation "/oc-acl:acl/oc-acl:acl-sets/oc-acl:acl-set/oc-acl:acl-entries/oc-acl:acl-entry/oc-acl:ipv6/oc-acl:state"  {
     deviate not-supported;
  }

   deviation "/oc-acl:acl/oc-acl:acl-sets/oc-acl:acl-set/oc-acl:acl-entries/oc-acl:acl-entry/oc-acl:transport/oc-acl:state"  {
     deviate not-supported;
  }

  deviation "/oc-acl:acl/oc-acl:acl-sets/oc-acl:acl-set/oc-acl:acl-entries/oc-acl:acl-entry/oc-acl:input-interface/oc-acl:state"  {
     deviate not-supported;
  }

  deviation "/oc-acl:acl/oc-acl:acl-sets/oc-acl:acl-set/oc-acl:acl-entries/oc-acl:acl-entry/oc-acl:actions/oc-acl:state"  {
     deviate not-supported;
  }

  deviation "/oc-acl:acl/oc-acl:interfaces/oc-acl:interface/oc-acl:state"{
     deviate not-supported;
  }

  deviation "/oc-acl:acl/oc-acl:interfaces/oc-acl:interface/oc-acl:interface-ref/oc-acl:state"{
     deviate not-supported;
  }

  deviation "/oc-acl:acl/oc-acl:interfaces/oc-acl:interface/oc-acl:ingress-acl-sets/oc-acl:ingress-acl-set/oc-acl:state"{
     deviate not-supported;
  }

  deviation "/oc-acl:acl/oc-acl:interfaces/oc-acl:interface/oc-acl:egress-acl-sets/oc-acl:egress-acl-set/oc-acl:state"{
     deviate not-supported;
  }

  // openconfig-qos deviations
  deviation "/oc-qos:qos/oc-qos:config" {
      description
          "Qos config is not supported";
      deviate not-supported;
  }
    deviation "/oc-qos:qos/oc-qos:state" {
      description
          "Qos state is not supported";
      deviate not-supported;
  }
  deviation /oc-qos:qos/oc-qos:scheduler-policies/oc-qos:scheduler-policy/oc-qos:schedulers/oc-qos:scheduler/oc-qos:output/oc-qos:config/oc-qos:child-scheduler {
      description
          "Child scheduler is not supported";
      deviate not-supported;
  }
  deviation /oc-qos:qos/oc-qos:scheduler-policies/oc-qos:scheduler-policy/oc-qos:schedulers/oc-qos:scheduler/oc-qos:two-rate-three-color/oc-qos:config/oc-qos:cir-pct-remaining {
      description
          "Remainder is not supported";
      deviate not-supported;
  }
  deviation /oc-qos:qos/oc-qos:scheduler-policies/oc-qos:scheduler-policy/oc-qos:schedulers/oc-qos:scheduler/oc-qos:two-rate-three-color/oc-qos:config/oc-qos:pir-pct-remaining {
      description
          "Remainder is not supported";
      deviate not-supported;
  }
  deviation /oc-qos:qos/oc-qos:scheduler-policies/oc-qos:scheduler-policy/oc-qos:schedulers/oc-qos:scheduler/oc-qos:two-rate-three-color/oc-qos:config/oc-qos:be {
      description
          "Excess burst size is not supported";
      deviate not-supported;
  }
  deviation /oc-qos:qos/oc-qos:scheduler-policies/oc-qos:scheduler-policy/oc-qos:schedulers/oc-qos:scheduler/oc-qos:inputs {
      description
          "Inputs section is not supported";
      deviate not-supported;
  }

  deviation /oc-qos:qos/oc-qos:interfaces/oc-qos:interface/oc-qos:output/oc-qos:interface-ref {
      description
          "/oc-qos:qos/oc-qos:interfaces/oc-qos:interface/oc-qos:interface-ref is used to specify interface and subinterface config. Hence output/interface-ref is redundant";
      deviate not-supported;
  }
  deviation "/oc-qos:qos/oc-qos:interfaces/oc-qos:interface/oc-qos:output/oc-qos:config" {
      description
          "/oc-qos:qos/oc-qos:interfaces/oc-qos:interface/oc-qos:config is not supported";
      deviate not-supported;
  }
  deviation "/oc-qos:qos/oc-qos:interfaces/oc-qos:interface/oc-qos:output/oc-qos:state" {
      description
          "/oc-qos:qos/oc-qos:interfaces/oc-qos:interface/oc-qos:state is not supported";
      deviate not-supported;
  }
  deviation "/oc-qos:qos/oc-qos:interfaces/" +
        "oc-qos:interface/oc-qos:input/oc-qos:virtual-output-queues/" +
        "oc-qos:voq-interface/oc-qos:queues/oc-qos:queue/oc-qos:state/" +
        "oc-qos:transmit-pkts" {
       description
            "transmit packets on voq ingress not supoorted";
       deviate not-supported;
  }
  deviation "/oc-qos:qos/oc-qos:interfaces/" +
        "oc-qos:interface/oc-qos:input/oc-qos:virtual-output-queues/" +
        "oc-qos:voq-interface/oc-qos:queues/oc-qos:queue/oc-qos:state/" +
        "oc-qos:transmit-octets" {
       description "transmit octets on ingress voq not supported";
       deviate not-supported;
  }
  deviation "/oc-qos:qos/oc-qos:buffer-allocation-profiles"{
      description
          "buffer allocation profiles are not supported";
      deviate not-supported;
  }
  deviation "/oc-qos:qos/oc-qos:queue-management-profiles/" +
        "oc-qos:queue-management-profile/oc-qos:red" {
      description
            "red profile is not supported";
      deviate not-supported;
  }
  // IGMP Deviations
  deviation "/oc-ni:network-instances/oc-ni:network-instance/oc-ni:protocols/oc-ni:protocol/oc-ni:igmp" {
     deviate not-supported;
  }
  // Pim Deviations

  deviation "/oc-ni:network-instances/oc-ni:network-instance/oc-ni:protocols/oc-ni:protocol" +
             "/oc-ni:pim/oc-ni:interfaces/oc-ni:interface/oc-ni:config" {
      description
           "Junos does not support PIM config";
      deviate not-supported;
  }

  deviation "/oc-ni:network-instances/oc-ni:network-instance/oc-ni:protocols/oc-ni:protocol" +
             "/oc-ni:pim/oc-ni:interfaces/oc-ni:interface/oc-ni:state" {
      description
           "Junos does not support PIM interface state";
      deviate not-supported;
  }

  deviation "/oc-ni:network-instances/oc-ni:network-instance/oc-ni:afts/oc-ni:policy-forwarding" {
      description
           "Not supported in this release";
      deviate not-supported;
  }

  deviation "/oc-ni:network-instances/oc-ni:network-instance/oc-ni:afts/oc-ni:ethernet" {
      description
           "Not supported in this release";
      deviate not-supported;
  }

  deviation "/oc-ni:network-instances/oc-ni:network-instance/oc-ni:afts/oc-ni:next-hops" +
             "/oc-ni:next-hop/oc-ni:ip-in-ip" {
      description
           "Not supported in this release";
      deviate not-supported;
  }

  deviation "/oc-ni:network-instances/oc-ni:network-instance/oc-ni:afts/oc-ni:ipv4-unicast" +
             "/oc-ni:ipv4-entry/oc-ni:state/oc-ni:entry-metadata" {
      description
           "Not supported in this release";
      deviate not-supported;
  }

  deviation /oc-system:system/oc-system:mount-points {
      description
          "Mount points is not supported";
      deviate not-supported;
  }

  deviation /oc-system:system/oc-system:license {
      description
          "License modelling is not supported";
      deviate not-supported;
  }

  deviation /oc-system:system/oc-system:messages {
      description
          "Syslog message is not supported";
      deviate not-supported;
  }

  deviation "/oc-telemetry:telemetry-system/oc-telemetry:subscriptions/oc-telemetry:dynamic-subscriptions" +
            "/oc-telemetry:dynamic-subscription/oc-telemetry:state/oc-telemetry:sample-interval" {
      deviate not-supported;
  }

  deviation "/oc-telemetry:telemetry-system/oc-telemetry:subscriptions/oc-telemetry:dynamic-subscriptions" +
            "/oc-telemetry:dynamic-subscription/oc-telemetry:state/oc-telemetry:heartbeat-interval" {
      deviate not-supported;
  }

  deviation "/oc-telemetry:telemetry-system/oc-telemetry:subscriptions/oc-telemetry:dynamic-subscriptions" +
            "/oc-telemetry:dynamic-subscription/oc-telemetry:state/oc-telemetry:suppress-redundant" {
      deviate not-supported;
  }

  deviation "/oc-telemetry:telemetry-system/oc-telemetry:subscriptions/oc-telemetry:dynamic-subscriptions" +
            "/oc-telemetry:dynamic-subscription/oc-telemetry:state/oc-telemetry:originated-qos-marking" {
      deviate not-supported;
  }

  deviation "/oc-telemetry:telemetry-system/oc-telemetry:subscriptions/oc-telemetry:dynamic-subscriptions" +
            "/oc-telemetry:dynamic-subscription/oc-telemetry:sensor-paths/oc-telemetry:sensor-path" +
            "/oc-telemetry:state/oc-telemetry:exclude-filter" {
      deviate not-supported;
  }
  deviation "/oc-telemetry:telemetry-system/oc-telemetry:subscriptions/oc-telemetry:persistent-subscriptions" +
            "/oc-telemetry:persistent-subscription/oc-telemetry:config/oc-telemetry:originated-qos-marking" {
      deviate not-supported;
  }

  deviation "/oc-telemetry:telemetry-system/oc-telemetry:subscriptions/oc-telemetry:persistent-subscriptions" +
            "/oc-telemetry:persistent-subscription/oc-telemetry:state" {
      deviate not-supported;
  }

  deviation "/oc-telemetry:telemetry-system/oc-telemetry:subscriptions/oc-telemetry:persistent-subscriptions" +
            "/oc-telemetry:persistent-subscription/oc-telemetry:sensor-profiles/oc-telemetry:sensor-profile/" +
	    "oc-telemetry:state" {
       deviate not-supported;
  }

  deviation "/oc-telemetry:telemetry-system/oc-telemetry:subscriptions/oc-telemetry:persistent-subscriptions" +
	    "/oc-telemetry:persistent-subscription/oc-telemetry:sensor-profiles/oc-telemetry:sensor-profile/" +
	    "oc-telemetry:config/oc-telemetry:heartbeat-interval" {
      deviate not-supported;
  }

  deviation "/oc-telemetry:telemetry-system/oc-telemetry:subscriptions/oc-telemetry:persistent-subscriptions" +
            "/oc-telemetry:persistent-subscription/oc-telemetry:sensor-profiles/oc-telemetry:sensor-profile/" +
            "oc-telemetry:config/oc-telemetry:suppress-redundant" {
      deviate not-supported;
  }

  deviation "/oc-telemetry:telemetry-system/oc-telemetry:sensor-groups/oc-telemetry:sensor-group/oc-telemetry:state" {
      deviate not-supported;
  }

  deviation "/oc-telemetry:telemetry-system/oc-telemetry:sensor-groups/oc-telemetry:sensor-group/oc-telemetry:sensor-paths" +
            "/oc-telemetry:sensor-path/oc-telemetry:config/oc-telemetry:exclude-filter" {
      deviate not-supported;
  }

  deviation "/oc-telemetry:telemetry-system/oc-telemetry:sensor-groups/oc-telemetry:sensor-group/oc-telemetry:sensor-paths" +
            "/oc-telemetry:sensor-path/oc-telemetry:state" {
      deviate not-supported;
  }

  deviation "/oc-telemetry:telemetry-system/oc-telemetry:destination-groups/oc-telemetry:destination-group/oc-telemetry:state" {
      deviate not-supported;
  }

  deviation "/oc-telemetry:telemetry-system/oc-telemetry:destination-groups/oc-telemetry:destination-group/oc-telemetry:destinations" +
            "/oc-telemetry:destination/oc-telemetry:state" {
      deviate not-supported;
  }
  
  deviation /oc-system:system/oc-sys-grpc:grpc-servers/oc-sys-grpc:grpc-server/oc-sys-grpc:state/oc-sys-grpc:network-instance {
      deviate not-supported;
  }

  /* OC MACsec deviations */
  deviation "/oc-msec:macsec/oc-msec:mka/oc-msec:policies/oc-msec:policy/oc-msec:config/oc-msec:include-icv-indicator"{
    deviate not-supported;
  }

  deviation "/oc-msec:macsec/oc-msec:mka/oc-msec:policies/oc-msec:policy/oc-msec:config/oc-msec:sak-rekey-on-live-peer-loss"{
    deviate not-supported;
  }

  deviation "/oc-msec:macsec/oc-msec:mka/oc-msec:policies/oc-msec:policy/oc-msec:config/oc-msec:use-updated-eth-header"{
    deviate not-supported;
  }

  deviation "/oc-msec:macsec/oc-msec:mka/oc-msec:policies/oc-msec:policy/oc-msec:config/oc-msec:sak-rekey-interval"{
    deviate replace {
      type uint32 {
        range 0..86400;
      }
    }
  }

  deviation "/oc-msec:macsec/oc-msec:mka/oc-msec:key-chains/oc-msec:key-chain/oc-msec:mka-keys/oc-msec:mka-key/oc-msec:id"{
    deviate replace {
      type string {
        length 4..66;
        pattern '([0-5][0-9]|6[0-3])[0-9a-fA-F]*';
      }
    }
  }

  deviation "/oc-msec:macsec/oc-msec:mka/oc-msec:key-chains/oc-msec:key-chain/oc-msec:mka-keys/oc-msec:mka-key/oc-msec:config/oc-msec:id"{
    deviate replace {
      type string {
        length 4..66;
        pattern '([0-5][0-9]|6[0-3])[0-9a-fA-F]*';
      }
    }
  }

  deviation "/oc-msec:macsec/oc-msec:mka/oc-msec:key-chains/oc-msec:key-chain/oc-msec:mka-keys/oc-msec:mka-key/oc-msec:config/oc-msec:key-clear-text"{
    deviate replace {
      type string {
        length 1..126;
      }
    }
  }

  deviation "/oc-msec:macsec/oc-msec:mka/oc-msec:key-chains/oc-msec:key-chain/oc-msec:mka-keys/oc-msec:mka-key/oc-msec:config/oc-msec:cryptographic-algorithm"{
    deviate not-supported;
  }

  deviation "/oc-msec:macsec/oc-msec:mka/oc-msec:key-chains/oc-msec:key-chain/oc-msec:mka-keys/oc-msec:mka-key/oc-msec:config/oc-msec:expiration-date-time"{
    deviate not-supported;
  }

  deviation "/oc-probes:probes/oc-probes:probe/oc-probes:config/oc-probes:name"{
      deviate not-supported;
  }
  deviation "/oc-probes:probes/oc-probes:probe/oc-probes:config/oc-probes:enabled"{
      deviate not-supported;
  }
  deviation "/oc-probes:probes/oc-probes:probe/oc-probes:tests/oc-probes:test/oc-probes:config/oc-probes:name"{
      deviate not-supported;
  }
  deviation "/oc-probes:probes/oc-probes:probe/oc-probes:tests/oc-probes:test/oc-probes:config/oc-probes:enabled"{
      deviate not-supported;
  }
  deviation "/oc-probes:probes/oc-probes:probe/oc-probes:tests/oc-probes:test/oc-probes:config/oc-probes:test-type"{
      deviate not-supported;
  }
  deviation "/oc-probes:probes/oc-probes:probe/oc-probes:tests/oc-probes:test/oc-probes:config/oc-probes:count"{
      deviate not-supported;
  }
  deviation "/oc-probes:probes/oc-probes:probe/oc-probes:tests/oc-probes:test/oc-probes:config/oc-probes:interval"{
      deviate not-supported;
  }
  deviation "/oc-probes:probes/oc-probes:probe/oc-probes:tests/oc-probes:test/oc-probes:config/oc-probes:source"{
      deviate not-supported;
  }
  deviation "/oc-probes:probes/oc-probes:probe/oc-probes:tests/oc-probes:test/oc-probes:config/oc-probes:history-size"{
      deviate not-supported;
  }
  deviation "/oc-probes:probes/oc-probes:probe/oc-probes:tests/oc-probes:test/oc-probes:config/oc-probes:source-port"{
      deviate not-supported;
  }
  deviation "/oc-probes:probes/oc-probes:probe/oc-probes:tests/oc-probes:test/oc-probes:config/oc-probes:dscp"{
      deviate not-supported;
  }
  deviation "/oc-probes:probes/oc-probes:probe/oc-probes:tests/oc-probes:test/oc-probes:target/oc-probes:config/oc-probes:address"{
      deviate not-supported;
  }
  deviation "/oc-probes:probes/oc-probes:probe/oc-probes:tests/oc-probes:test/oc-probes:target/oc-probes:config/oc-probes:port"{
      deviate not-supported;
  }
  deviation "/oc-probes:probes/oc-probes:probe/oc-probes:tests/oc-probes:test/oc-probes:target/oc-probes:config/oc-probes:url"{
      deviate not-supported;
  }
  deviation "/oc-probes:probes/oc-probes:probe/oc-probes:tests/oc-probes:test/oc-probes:target/oc-probes:state/oc-probes:url"{
      deviate not-supported;
  }
}
