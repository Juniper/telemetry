module junos-yang-types {

    yang-version "1";

    namespace "http://juniper.net/yang/types";

    prefix "jnx-types";


    organization "Juniper Networks";

    revision "2021-03-08" {
        description "Junos specific types defined";
        reference "1.0.0";
    }

  typedef vlan-range {
    type string {
      // range specified as [lower]..[upper]
      pattern '(409[0-4]|40[0-8][0-9]|[1-3][0-9]{3}|'       +
              '[1-9][0-9]{1,2}|[1-9])\.\.(409[0-4]|'       +
              '40[0-8][0-9]|[1-3][0-9]{3}|[1-9][0-9]{1,2}|' +
              '[1-9])';
    }
    description
      "Type definition representing a range of single-tagged
      VLANs. A range is specified as x..y where x and y are
      valid VLAN IDs (1 <= vlan-id <= 4094). The range is
      assumed to be inclusive, such that any VLAN-ID matching
      x <= VLAN-ID <= y falls within the range.";
  }

  typedef port-range {
     type string {
     // range specified as [lower]..[upper]
     pattern '(6553[0-5]|655[0-2][0-9]|65[0-4][0-9]{2}|' +
             '6[0-4][0-9]{3}|[0-5][0-9]{4}|[0-9]{1,4})\.\.' +
             '(6553[0-5]|655[0-2][0-9]|65[0-4][0-9]{2}|' +
             '6[0-4][0-9]{3}|[0-5][0-9]{4}|[0-9]{1,4})';
     }
     description
     "Port numbers may be represented as a single value,
     an inclusive range as <lower>..<higher>.";
  }

}
