module junos-state-mist-types {
  yang-version 1.1;
  namespace "http://yang.juniper.net/junos/state/mist/types";
  prefix js-mist-types;

  import junos-base-extensions {
    prefix junos-base;
  }

  organization
    "Juniper Networks, Inc.";

  contact
    "Juniper Networks, Inc.

     1133 Innovation Way
     Sunnyvale, CA

     +1 888 314-5822

     E-mail: yang-support@juniper.net";

  description
    "This module contains a collection of JUNOS Mist Cloud data types.

     Copyright (c) 2022 Juniper Networks, Inc.
     All rights reserved.";

  revision 2022-03-14 {
    description
      "Initial revision";
    reference "0.1.0";
  }

  junos-base:version "0.1.0";

  typedef connectivity-state {
    type enumeration {
      enum DAY0_BOOTING {
        value 1;
        description
          "Day-0: Success: Booting";
      }
      enum DAY0_BOOT_FAILED {
        value 2;
        description
          "Day-0: Failure: Boot failed";
      }
      enum DAY0_BOOT_COMPLETE {
        value 3;
        description
          "Day-0: Success: Boot complete";
      }
      enum DAY0_NO_IP_ADDRESS {
        value 4;
        description
          "Day-0: Failure: No IP address";
      }
      enum DAY0_NO_DEFAULT_GW {
        value 5;
        description
          "Day-0: Failure: No default gateway";
      }
      enum DAY0_DEFAULT_GW_UNREACHABLE {
        value 6;
        description
          "Day-0: Failure: Default gateway unreachable";
      }
      enum DAY0_NO_DNS {
        value 7;
        description
          "Day-0: Failure: No DNS";
      }
      enum DAY0_DNS_LOOKUP_FAILED {
        value 8;
        description
          "Day-0: Failure: DNS lookup failed";
      }
      enum DAY0_NO_DNS_RESPONSE_REDIRECT {
        value 9;
        description
          "Day-0: Failure: No DNS response - redirect";
      }
      enum DAY0_EMPTY_DNS_RESPONSE_REDIRECT {
        value 10;
        description
          "Day-0: Failure: Empty DNS response - redirect";
      }
      enum DAY0_CLOUD_UNREACHABLE_REDIRECT {
        value 11;
        description
          "Day-0: Failure: Cloud unreachable - redirect";
      }
      enum DAY0_NO_CLOUD_RESPONSE {
        value 12;
        description
          "Day-0: Failure: No cloud response";
      }
      enum DAY0_CLOUD_CERT_TIME_CHECK_FAILED {
        value 13;
        description
          "Day-0: Failure: Cloud certifiate time check failed";
      }
      enum DAY0_CLOUD_CERT_INVALID {
        value 14;
        description
          "Day-0: Failure: Cloud certificate invalid";
      }
      enum DAY0_CONNECTED_TO_REDIRECT {
        value 15;
        description
          "Day-0: Success: Connected to redirect";
      }
      enum DAY0_REDIRECT_SUPPLIED_CONFIG_SERVER_DETAILS {
        value 16;
        description
          "Day-0: Success: Redirect supplied config server details";
      }
      enum DAY0_REDIRECT_DID_NOT_SUPPLY_VALID_CONFIG_SERVER_DETAILS {
        value 17;
        description
          "Day-0: Failure: Redirect did not supply valid config server
          details";
      }
      enum DAY0_CONNECTED_TO_CONFIG_SERVER {
        value 18;
        description
          "Day-0: Success: Connected to config server";
      }
      enum DAY0_NO_DNS_RESPONSE_CONFIG {
        value 19;
        description
          "Day-0: Failure: No DNS response - config";
      }
      enum DAY0_EMPTY_DNS_RESPONSE_CONFIG {
        value 20;
        description
          "Day-0: Failure: Empty DNS response - config";
      }
      enum DAY0_CLOUD_UNREACHABLE_CONFIG {
        value 21;
        description
          "Day-0: Failure: Cloud unreachable - config";
      }
      enum DAY0_SW_DOWNLOAD_FAILURE {
        value 22;
        description
          "Day-0: Failure: SW download failure";
      }
      enum DAY0_SW_DOWNLOAD_COMPLETE {
        value 23;
        description
          "Day-0: Success: SW download complete";
      }
      enum BOOTING {
        value 24;
        description
          "Day-1: Success: Booting";
      }
      enum BOOT_FAILED {
        value 25;
        description
          "Day-1: Failure: Boot failed";
      }
      enum BOOT_COMPLETE {
        value 26;
        description
          "Day-1: Success: Boot complete";
      }
      enum NO_IP_ADDRESS {
        value 27;
        description
          "Day-1: Failure: No IP address";
      }
      enum NO_DEFAULT_GW {
        value 28;
        description
          "Day-1: Failure: No default gateway";
      }
      enum DEFAULT_GW_UNREACHABLE {
        value 29;
        description
          "Day-1: Failure: Default gateway unreachable";
      }
      enum NO_DNS {
        value 30;
        description
          "Day-1: Failure: No DNS";
      }
      enum DNS_LOOKUP_FAILED {
        value 31;
        description
          "Day-1: Failure: DNS lookup failed";
      }
      enum NO_DNS_RESPONSE_REDIRECT {
        value 32;
        description
          "Day-1: Failure: No DNS response - redirect";
      }
      enum EMPTY_DNS_RESPONSE_REDIRECT {
        value 33;
        description
          "Day-1: Failure: Empty DNS response - redirect";
      }
      enum CONNECTION_REG_SENT_TO_MIST_CLOUD {
        value 34;
        description
          "Day-1: Success: Connection request sent to Mist cloud";
      }
      enum CLOUD_UNREACHABLE_MIST_CLOUD {
        value 35;
        description
          "Day-1: Failure: Cloud unreachable - Mist cloud";
      }
      enum CLOUD_UNREACHABLE_AUTH_FAILURE_MIST_CLOUD {
        value 36;
        description
          "Day-1: Failure: Cloud unreachable due to auth failure - Mist cloud";
      }
      enum UNDERLYING_SERVICE_DOWN {
        value 37;
        description
          "Day-1: Failure: Underlying service down";
      }
      enum CONNECTED_TO_MIST_CLOUD {
        value 38;
        description
          "Day-1: Success: Connected to Mist cloud";
      }
      enum HEALTH_ISSUE_TO_MIST_CLOUD {
        value 39;
        description
          "Day-1: Degraded: Health issue to Mist cloud connection";
      }
      enum SW_DOWNLOAD_FAILURE {
        value 40;
        description
          "Day-1: Failure: SW download failure";
      }
      enum SW_DOWNLOAD_COMPLETE {
        value 41;
        description
          "Day-1: Success: SW Download complete";
      }
    }
    description
      "This value represents the current Mist cloud connectivity state
       of the system.";
  }
}
