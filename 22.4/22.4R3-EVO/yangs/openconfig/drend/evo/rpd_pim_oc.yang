module rpd_pim_oc {
  yang-version 1;

  namespace "http://juniper.net/yang/pim_oc_render";

  prefix "pim_oc";

  import drend {
    prefix "dr";
  }

  import jnpr-proto { prefix jnpr-proto; }
  import openconfig-pim { prefix oc-pim; }

  description "
    Rendering Junos PIM State in OpenConfig PIM Schema terms
  ";

  dr:command-app "rpd";
  dr:sub-component "PIM";
  jnpr-proto:message-id "RPD-PIM-OC-MESSAGE-ID";

  grouping rend-pim-neighbor-state {
    uses oc-pim:pim-neighbor-state {
    augment "neighbor-address" {
      dr:source "neighbor-address";
      dr:fieldnum 51;
    }
    augment "dr-address" {
      dr:source "dr-address";
      dr:fieldnum 52;
    }
    augment "neighbor-established" {
      dr:source "neighbor-established";
      dr:fieldnum 53;
    }
    augment "neighbor-expires" {
      dr:source "neighbor-expires";
      dr:fieldnum 54;
    }
    augment "mode" {
      dr:source "mode";
      dr:fieldnum 55;
    }
   }
  }

  grouping rend-network-instance-top {
    uses oc-pim:pim-interfaces-top {
      augment "interfaces" {
        dr:fieldnum 151;
      }
      augment "interfaces/interface" {
        dr:source "pim/interfaces/interface";
        dr:fieldnum 151;
      }
      augment "interfaces/interface/interface-id" {
        dr:source "name";
        dr:fieldnum 51;
      }
      augment "interfaces/interface/neighbors" {
        dr:fieldnum 151;
      }
      augment "interfaces/interface/neighbors/neighbor" {
        dr:source "neighbors/neighbor";
        dr:fieldnum 151;
        dr:source-notification-name "pim-nbr-state-change";
      }
      augment "interfaces/interface/neighbors/neighbor/neighbor-address" {
        dr:source "neighbor-address";
        dr:fieldnum 51;
      }
      augment "interfaces/interface/neighbors/neighbor/state" {
        dr:fieldnum 151;
      }
      augment "interfaces/interface/neighbors/neighbor/state/neighbor-address" {
        dr:source "neighbor-address";
        dr:fieldnum 51;
      }
      augment "interfaces/interface/neighbors/neighbor/state/dr-address" {
        dr:source "dr-address";
        dr:fieldnum 52;
      }
      augment "interfaces/interface/neighbors/neighbor/state/neighbor-established" {
        dr:source "neighbor-established";
        dr:fieldnum 53;
      }
      augment "interfaces/interface/neighbors/neighbor/state/neighbor-expires" {
        dr:source "neighbor-expires";
        dr:fieldnum 54;
      }
      augment "interfaces/interface/neighbors/neighbor/state/mode" {
        dr:source "mode";
        dr:fieldnum 55;
      }
    }
  }

  rpc juniper-netconf-get {
    dr:command-top-of-output "/oc-pim-information";
    dr:command-full-name "request drend juniper-netconf-get";
    dr:command-help "Default <get> rpc";

    output {
      container network-instances {
         list network-instance {
           key "name";
           dr:source "/rt-instances/rt-instance";
           dr:fieldnum 151;

           leaf name {
             type string;
             dr:source "instance_name";
             dr:fieldnum 51;
           }

           container protocols {
             dr:fieldnum 151;
             container protocol {
               dr:source "protocols/protocol";
               dr:fieldnum 151;

               container pim {
                 dr:fieldnum 151;
                 uses rend-network-instance-top;
               }
             }
           }
         }
      }
    }
  }

  /* On Change notifications */
  notification oc-pim-nbr-state-change {
    dr:source-notification-name "pim-nbr-state-change";
    container network-instances {
      dr:source "/notification/pim-nbr-state-change/network-instances";
      dr:fieldnum 151;
      list network-instance {
        dr:source "network-instance";
        dr:fieldnum 151;
        key name;
        leaf name {
          type string;
          dr:source "instance-name";
          dr:fieldnum 51;
        }
        container protocols {
          dr:fieldnum 151;
          container protocol {
            dr:fieldnum 151;
            container pim {
              dr:fieldnum 151;
              container interfaces {
                dr:fieldnum 151;
                list interface {
                  dr:source "interfaces/interface";
                  dr:fieldnum 151;
                  key interface-id;
                  leaf interface-id {
                    dr:source "name";
                    type string;
                    dr:fieldnum 51;
                  }
                  container neighbors {
                    dr:fieldnum 151;
                    list neighbor {
                      dr:source "neighbors/neighbor";
                      dr:fieldnum 151;
                      key "neighbor-address";
                      leaf neighbor-address {
                        dr:source "neighbor-address";
                        dr:fieldnum 51;
                        type leafref {
                          path "../state/neighbor-address";
                        }
                      }
                      container state {
                        dr:fieldnum 151;
                        uses rend-pim-neighbor-state;
                      }
                    }
                  }
                }
              }
            }
          }
        }
      }
    }
  }
    /*
     * TODO: FIX it (in rendering file we need to have augment statement
     * (do not use containers and list statement)
     * The following changes are not working (on-change notification is not
     * sent with below changes)
     *
    uses oc-ni:network-instance-top {
      augment "network-instances" {
        dr:source "/notification/pim-nbr-state-change/network-instances";
        dr:fieldnum 151;
      }
      augment "network-instances/network-instance" {
        dr:source "network-instance";
        dr:fieldnum 151;
      }
      augment "network-instances/network-instance/name" {
        dr:source "instance-name";
        dr:fieldnum 51;
      }

      augment "network-instances/network-instance/protocols" {
        dr:fieldnum 151;
      }
      augment "network-instances/network-instance/protocols/protocol" {
        dr:fieldnum 151;
      }
      augment "network-instances/network-instance/protocols/protocol/pim" {
        dr:fieldnum 151;
      }
      augment "network-instances/network-instance/protocols/protocol/pim/interfaces" {
        dr:fieldnum 151;
      }
      augment "network-instances/network-instance/protocols/protocol/pim/interfaces/interface" {
        dr:source "interfaces/interface";
        dr:fieldnum 151;
      }
      augment "network-instances/network-instance/protocols/protocol/pim/interfaces/interface/interface-id" {
        dr:source "name";
        dr:fieldnum 51;
      }
      augment "network-instances/network-instance/protocols/protocol/pim/interfaces/interface/neighbors" {
        dr:fieldnum 151;
      }
      augment "network-instances/network-instance/protocols/protocol/pim/interfaces/interface/neighbors/neighbor" {
        dr:source "neighbors/neighbor";
        dr:fieldnum 151;
      }
      augment "network-instances/network-instance/protocols/protocol/pim/interfaces/interface/neighbors/neighbor/neighbor-address" {
        dr:source "neighbor-address";
        dr:fieldnum 51;
      }
      augment "network-instances/network-instance/protocols/protocol/pim/interfaces/interface/neighbors/neighbor/state" {
        dr:fieldnum 151;
      }
      augment "network-instances/network-instance/protocols/protocol/pim/interfaces/interface/neighbors/neighbor/state/neighbor-address" {
        dr:source "neighbor-address";
        dr:fieldnum 51;
      }
      augment "network-instances/network-instance/protocols/protocol/pim/interfaces/interface/neighbors/neighbor/state/dr-address" {
        dr:source "dr-address";
        dr:fieldnum 52;
      }
      augment "network-instances/network-instance/protocols/protocol/pim/interfaces/interface/neighbors/neighbor/state/neighbor-established" {
        dr:source "neighbor-established";
        dr:fieldnum 53;
      }
      augment "network-instances/network-instance/protocols/protocol/pim/interfaces/interface/neighbors/neighbor/state/neighbor-expires" {
        dr:source "neighbor-expires";
        dr:fieldnum 54;
      }
      augment "network-instances/network-instance/protocols/protocol/pim/interfaces/interface/neighbors/neighbor/state/mode" {
        dr:source "mode";
        dr:fieldnum 55;
      }
    }
  } */
}
