/*
* $Id$
*
* Copyright (c) 2018, Juniper Networks, Inc.
* All rights reserved.
*
*/
 
module hwdre_oc {
 
  yang-version "1";
 
  // namespace
  namespace "http://juniper.net/yang/hwdre-oc";
 
  prefix "hwdre-oc";
 
  import openconfig-platform { prefix oc-pf; }
  import openconfig-platform-fan { prefix oc-fan; }
  import openconfig-platform-psu { prefix oc-psu; }
  import drend { prefix dr; }
  import openconfig-platform-linecard { prefix oc-linecard; }
  import jnpr-proto { prefix jnpr-proto; }
  import jnx-aug-openconfig-platform { prefix jnx-oc-pf; }
  import jnx-aug-openconfig-platform { prefix jnx-oc-platform; }

  // meta
  organization "Juniper Networks Inc.";
 
  contact "www.juniper.net";

  grouping chassisd-inventory {
      uses oc-pf:platform-component-top {
      augment "components" {
        dr:source "/evl_types:JunosOperState";
        dr:fieldnum 151;
      }
      augment "components/component" {
        dr:source "hwd_module:fruE";
        dr:source-notification-name "hwd_module:fruE-event";
        dr:source-notification-name "hwd_module:subcomponentE-event";
        dr:fieldnum 151;
        uses jnx-oc-pf:control-card-info {
          augment "control-card" {
            dr:fieldnum 168;
          }
          augment "control-card/properties" {
            dr:fieldnum 152;
          }
          augment "control-card/properties/property" {
            dr:source "cbPropertyE";
            dr:fieldnum 151;
          }
          augment "control-card/properties/property/name" {
            dr:source "name";
            dr:fieldnum 51;
          }
          augment "control-card/properties/property/state" {
            dr:fieldnum 151;
          }
          augment "control-card/properties/property/state/value" {
            dr:source "value";
            dr:fieldnum 51;
          }
          augment "control-card/properties/property/state/configurable" {
            dr:source "configurable";
            dr:fieldnum 52;
          }
        }
        uses oc-linecard:linecard-top {
          augment "linecard" {
             dr:fieldnum 161;
          }
          augment "linecard/state" {
            dr:fieldnum 151;
              uses jnx-oc-pf:linecard-info {
                augment "boot-time" {
                  dr:source "telemetryFpcData/bootTime";
                  dr:zero-suppressed;
                  dr:fieldnum 51;
                }
                augment "recent-reset-cause" {
                  dr:source "telemetryFpcData/resetReason";
                  dr:zero-suppressed;
                  dr:fieldnum 52;
                }
              }
              uses jnx-oc-platform:hwd-component-state-info {
                augment "type" {
                  dr:source "telemetryFpcData/fruType";
                  dr:fieldnum 55;
                  dr:map LINECARD         { dr:map-from 9 ; } // FPC;
                }
                augment "id" {
                  dr:source "telemetryFpcData/serialNumber";
                  dr:zero-suppressed;
                  dr:fieldnum 56;
                }
                augment "description" {
                  dr:source "telemetryFpcData/description";
                  dr:fieldnum 57;
                }
                augment "serial-no" {
                  dr:source "telemetryFpcData/serialNumber";
                  dr:zero-suppressed;
                  dr:fieldnum 58;
                }
                augment "part-no" {
                  dr:source "telemetryFpcData/partNumber";
                  dr:zero-suppressed;
                  dr:fieldnum 59;
                }
                augment "hardware-version" {
                  dr:source "telemetryFpcData/version";
                  dr:zero-suppressed;
                  dr:fieldnum 60;
                }
                augment "oper-status" {
                  dr:source "telemetryFpcData/state";
                  dr:fieldnum 61;
                  dr:map INACTIVE             { dr:map-from 3 ; } // Present
                  dr:map ACTIVE               { dr:map-from 8 ; } // Online
                  dr:map DISABLED             { dr:map-from 10; } // Offline
                  dr:map DISABLED             { dr:map-from 12; } // Standby
                  dr:map INACTIVE             { dr:map-from 14; } // Fault
                  dr:map INACTIVE             { dr:map-from 15; } // Fault Power Off
                  dr:map DISABLED             { dr:map-from 18; } // Power off
                }
                augment "location" {
                  dr:source "telemetryFpcData/location";
                  dr:fieldnum 62;
                }
                augment "mfg-name" {
                  dr:source "telemetryFpcData/mfg_name";
                  dr:zero-suppressed;
                  dr:fieldnum 63;
                }
                augment "mfg-date" {
                  dr:source "telemetryFpcData/manufactureDate";
                  dr:zero-suppressed;
                  dr:fieldnum 64;
                }
                augment "firmware-version" {
                  dr:source "telemetryFpcData/firmware_version";
                  dr:zero-suppressed;
                  dr:fieldnum 65;
                }
                augment "software-version" {
                  dr:source "telemetryFpcData/software_version";
                  dr:zero-suppressed;
                  dr:fieldnum 66;
                }
                augment "removable" {
                  dr:source "telemetryFpcData/is_removable";
                  dr:fieldnum 67;
                }
                augment "empty" {
                  dr:source "telemetryFpcData/empty";
                  dr:fieldnum 68;
                }
                augment "parent" {
                  dr:source "telemetryFpcData/parent";
                  dr:fieldnum 69;
                }
              }
            }
            augment "linecard/state/power-admin-state" {
              dr:source "telemetryFpcData/state";
              dr:fieldnum 152;
              dr:map POWER_ENABLED         { dr:map-from 3 ; } // Present
              dr:map POWER_ENABLED         { dr:map-from 8 ; } // Online
              dr:map POWER_DISABLED        { dr:map-from 10; } // Offline
              dr:map POWER_ENABLED         { dr:map-from 14; } // Fault
              dr:map POWER_DISABLED        { dr:map-from 15; } // Fault Power Off
              dr:map POWER_DISABLED        { dr:map-from 18; } // Power off
            }
            augment "linecard/state/slot-id" {
              dr:source "telemetryFpcData/slot";
              dr:fieldnum 153;
            }
        }
      }
      augment "components/component/chassis" {
        dr:fieldnum 154;
        uses jnx-oc-pf:hwd-component-property-info {
          augment "properties" {
            dr:fieldnum 152;
          }
          augment "properties/property" {
            dr:source "chasPropertyE";
            dr:fieldnum 151;
          }
          augment "properties/property/name" {
            dr:source "name";
            dr:fieldnum 51;
          }
          augment "properties/property/state" {
            dr:fieldnum 151;
          }
          augment "properties/property/state/value" {
            dr:source "value";
            dr:fieldnum 51;
          }
          augment "properties/property/state/configurable" {
            dr:source "configurable";
            dr:fieldnum 52;
          }
        }
      }
      augment "components/component/chassis/state" {
          dr:fieldnum 151;
          uses jnx-oc-pf:chassis-info {
              augment "base-mac-address" {
                  dr:source "telemetryChassisData/baseAddr";
                  dr:zero-suppressed;
                  dr:fieldnum 71;
              }
              augment "base-num-mac-addresses" {
                  dr:source "telemetryChassisData/numBaseAddr";
                  dr:zero-suppressed;
                  dr:fieldnum 72;
              }
          }
      }

      /*fan data */
      augment "components/component/fan" {
        dr:fieldnum 153;
      }
      augment "components/component/fan/state" {
        dr:fieldnum 151;
        uses oc-fan:fan-state {
          augment "speed" {
            dr:zero-suppressed;
            dr:source "fan_speed";
            dr:fieldnum 51;
          }
        }
        uses jnx-oc-platform:hwd-component-state-info {
          augment "type" {
            dr:source "telemetryFanData/fruType";
            dr:fieldnum 53;
            dr:map FAN    { dr:map-from 14; } // FAN;
          }
          augment "id" {
            dr:source "telemetryFanData/serialNumber";
            dr:zero-suppressed;
            dr:fieldnum 54;
          }
          augment "description" {
            dr:source "telemetryFanData/description";
            dr:fieldnum 55;
          }
          augment "serial-no" {
            dr:source "telemetryFanData/serialNumber";
            dr:zero-suppressed;
            dr:fieldnum 56;
          }
          augment "part-no" {
            dr:source "telemetryFanData/partNumber";
            dr:zero-suppressed;
            dr:fieldnum 57;
          }
          augment "hardware-version" {
            dr:source "telemetryFanData/version";
            dr:zero-suppressed;
            dr:fieldnum 58;
          }
          augment "oper-status" {
            dr:source "telemetryFanData/state";
            dr:fieldnum 59;
            dr:map INACTIVE             { dr:map-from 3 ; } // Present
            dr:map ACTIVE               { dr:map-from 8 ; } // Online
            dr:map DISABLED             { dr:map-from 10; } // Offline
            dr:map DISABLED             { dr:map-from 12; } // Standby
            dr:map INACTIVE             { dr:map-from 14; } // Fault
            dr:map INACTIVE             { dr:map-from 15; } // Fault Power Off
            dr:map DISABLED             { dr:map-from 18; } // Power off
          }
          augment "location" {
            dr:source "telemetryFanData/location";
            dr:fieldnum 60;
          }
          augment "mfg-name" {
            dr:source "telemetryFanData/mfg_name";
            dr:zero-suppressed;
            dr:fieldnum 61;
          }
          augment "mfg-date" {
            dr:source "telemetryFanData/manufactureDate";
            dr:zero-suppressed;
            dr:fieldnum 62;
          }
          augment "firmware-version" {
            dr:source "telemetryFanData/firmware_version";
            dr:zero-suppressed;
            dr:fieldnum 63;
          }
          augment "software-version" {
            dr:source "telemetryFanData/software_version";
            dr:zero-suppressed;
            dr:fieldnum 64;
          }
          augment "removable" {
            dr:source "telemetryFanData/is_removable";
            dr:fieldnum 65;
          }
          augment "empty" {
            dr:source "telemetryFanData/empty";
            dr:fieldnum 66;
          }
          augment "parent" {
            dr:source "telemetryFanData/parent";
            dr:fieldnum 67;
          }
        }
      }

      /*power-supply data */
      augment "components/component/power-supply" {
        dr:fieldnum 155;
      }
      augment "components/component/power-supply/state" {
        dr:fieldnum 151;
        uses oc-psu:psu-state {
          augment "capacity" {
            dr:zero-suppressed;
            dr:source "telemetryPsmData/capacity_flt";
            dr:fieldnum 51;
          }
          augment "input-current" {
            dr:zero-suppressed;
            dr:source "telemetryPsmData/input_current_flt";
            dr:fieldnum 52;
          }
          augment "input-voltage" {
            dr:zero-suppressed;
            dr:source "telemetryPsmData/input_voltage_flt";
            dr:fieldnum 53;
          }
          augment "output-current" {
            dr:zero-suppressed;
            dr:source "telemetryPsmData/output_current_flt";
            dr:fieldnum 54;
          }
          augment "output-voltage" {
            dr:zero-suppressed;
            dr:source "telemetryPsmData/output_voltage_flt";
            dr:fieldnum 55;
          }
          augment "output-power" {
            dr:zero-suppressed;
            dr:source "telemetryPsmData/output_power_flt";
            dr:fieldnum 56;
          }
        }
        uses jnx-oc-platform:hwd-component-state-info {
          augment "type" {
            dr:source "telemetryPsmData/fruType";
            dr:fieldnum 58;
            dr:map POWER_SUPPLY     { dr:map-from 5 ; } // PSM;
          }
          augment "id" {
            dr:source "telemetryPsmData/serialNumber";
            dr:zero-suppressed;
            dr:fieldnum 59;
          }
          augment "description" {
            dr:source "telemetryPsmData/description";
            dr:fieldnum 60;
          }
          augment "serial-no" {
            dr:source "telemetryPsmData/serialNumber";
            dr:zero-suppressed;
            dr:fieldnum 61;
          }
          augment "part-no" {
            dr:source "telemetryPsmData/partNumber";
            dr:zero-suppressed;
            dr:fieldnum 62;
          }
          augment "hardware-version" {
            dr:source "telemetryPsmData/version";
            dr:zero-suppressed;
            dr:fieldnum 63;
          }
          augment "oper-status" {
            dr:source "telemetryPsmData/state";
            dr:fieldnum 64;
            dr:map INACTIVE             { dr:map-from 3 ; } // Present
            dr:map ACTIVE               { dr:map-from 8 ; } // Online
            dr:map DISABLED             { dr:map-from 10; } // Offline
            dr:map DISABLED             { dr:map-from 12; } // Standby
            dr:map INACTIVE             { dr:map-from 14; } // Fault
            dr:map INACTIVE             { dr:map-from 15; } // Fault Power Off
            dr:map DISABLED             { dr:map-from 18; } // Power off
          }
          augment "location" {
            dr:source "telemetryPsmData/location";
            dr:fieldnum 65;
          }
          augment "mfg-name" {
            dr:source "telemetryPsmData/mfg_name";
            dr:zero-suppressed;
            dr:fieldnum 66;
          }
          augment "mfg-date" {
            dr:source "telemetryPsmData/manufactureDate";
            dr:zero-suppressed;
            dr:fieldnum 67;
          }
          augment "firmware-version" {
            dr:source "telemetryPsmData/firmware_version";
            dr:zero-suppressed;
            dr:fieldnum 68;
          }
          augment "software-version" {
            dr:source "telemetryPsmData/software_version";
            dr:zero-suppressed;
            dr:fieldnum 69;
          }
          augment "removable" {
            dr:source "telemetryPsmData/is_removable";
            dr:fieldnum 70;
          }
          augment "empty" {
            dr:source "telemetryPsmData/empty";
            dr:fieldnum 71;
          }
          augment "parent" {
            dr:source "telemetryPsmData/parent";
            dr:fieldnum 72;
          }
        }
      }

      augment "components/component/backplane" {
        dr:fieldnum 165;
      }
      augment "components/component/backplane/state" {
        dr:fieldnum 165;
        uses jnx-oc-platform:hwd-component-state-info {

        augment "type" {
          dr:source "telemetryBpData/fruType";
          dr:fieldnum 52;
          dr:map BACKPLANE { dr:map-from 2 ; } // BACKPLANE;
        }
        augment "id" {
          dr:source "telemetryBpData/serialNumber";
          dr:zero-suppressed;
          dr:fieldnum 53;
        }
        augment "description" {
          dr:source "telemetryBpData/description";
          dr:fieldnum 54;
        }
        augment "serial-no" {
          dr:source "telemetryBpData/serialNumber";
          dr:zero-suppressed;
          dr:fieldnum 55;
        }
        augment "part-no" {
          dr:source "telemetryBpData/partNumber";
          dr:zero-suppressed;
          dr:fieldnum 56;
        }
        augment "hardware-version" {
          dr:source "telemetryBpData/version";
          dr:zero-suppressed;
          dr:fieldnum 57;
        }
        augment "oper-status" {
          dr:source "telemetryBpData/state";
          dr:fieldnum 58;
          dr:map INACTIVE             { dr:map-from 3 ; } // Present
          dr:map ACTIVE               { dr:map-from 8 ; } // Online
          dr:map DISABLED             { dr:map-from 10; } // Offline
          dr:map DISABLED             { dr:map-from 12; } // Standby
          dr:map INACTIVE             { dr:map-from 14; } // Fault
          dr:map INACTIVE             { dr:map-from 15; } // Fault Power Off
          dr:map DISABLED             { dr:map-from 18; } // Power off
        }
        augment "location" {
          dr:source "telemetryBpData/location";
          dr:fieldnum 59;
        }
        augment "mfg-name" {
          dr:source "telemetryBpData/mfg_name";
          dr:zero-suppressed;
          dr:fieldnum 60;
        }
        augment "mfg-date" {
          dr:source "telemetryBpData/manufactureDate";
          dr:zero-suppressed;
          dr:fieldnum 61;
        }
        augment "firmware-version" {
          dr:source "telemetryBpData/firmware_version";
          dr:zero-suppressed;
          dr:fieldnum 62;
        }
        augment "software-version" {
          dr:source "telemetryBpData/software_version";
          dr:zero-suppressed;
          dr:fieldnum 63;
        }
        augment "removable" {
          dr:source "telemetryBpData/is_removable";
          dr:fieldnum 64;
        }
        augment "empty" {
          dr:source "telemetryBpData/empty";
          dr:fieldnum 65;
        }
        augment "parent" {
          dr:source "telemetryBpData/parent";
          dr:fieldnum 66;
        }
       }
      }
      augment "components/component/fabric" {
        dr:fieldnum 166;
      }
      augment "components/component/fabric/state" {
        dr:fieldnum 166;
        uses jnx-oc-platform:hwd-component-state-info {
        augment "type" {
          dr:source "telemetrySibData/fruType";
          dr:fieldnum 52;
          dr:map FABRIC   { dr:map-from 12; } // SIB;
        }
        augment "id" {
          dr:source "telemetrySibData/serialNumber";
          dr:zero-suppressed;
          dr:fieldnum 53;
        }
        augment "description" {
          dr:source "telemetrySibData/description";
          dr:fieldnum 54;
        }
        augment "serial-no" {
          dr:source "telemetrySibData/serialNumber";
          dr:zero-suppressed;
          dr:fieldnum 55;
        }
        augment "part-no" {
          dr:source "telemetrySibData/partNumber";
          dr:zero-suppressed;
          dr:fieldnum 56;
        }
        augment "hardware-version" {
          dr:source "telemetrySibData/version";
          dr:zero-suppressed;
          dr:fieldnum 57;
        }
        augment "oper-status" {
          dr:source "telemetrySibData/state";
          dr:fieldnum 58;
          dr:map INACTIVE             { dr:map-from 3 ; } // Present
          dr:map ACTIVE               { dr:map-from 8 ; } // Online
          dr:map DISABLED             { dr:map-from 10; } // Offline
          dr:map DISABLED             { dr:map-from 12; } // Standby
          dr:map INACTIVE             { dr:map-from 14; } // Fault
          dr:map INACTIVE             { dr:map-from 15; } // Fault Power Off
          dr:map DISABLED             { dr:map-from 18; } // Power off
        }
        augment "location" {
          dr:source "telemetrySibData/location";
          dr:fieldnum 59;
        }
        augment "mfg-name" {
          dr:source "telemetrySibData/mfg_name";
          dr:zero-suppressed;
          dr:fieldnum 60;
        }
        augment "mfg-date" {
          dr:source "telemetrySibData/manufactureDate";
          dr:zero-suppressed;
          dr:fieldnum 61;
        }
        augment "firmware-version" {
          dr:source "telemetrySibData/firmware_version";
          dr:zero-suppressed;
          dr:fieldnum 62;
        }
        augment "software-version" {
          dr:source "telemetrySibData/software_version";
          dr:zero-suppressed;
          dr:fieldnum 63;
        }
        augment "removable" {
          dr:source "telemetrySibData/is_removable";
          dr:fieldnum 64;
        }
        augment "empty" {
          dr:source "telemetrySibData/empty";
          dr:fieldnum 65;
        }
        augment "parent" {
          dr:source "telemetrySibData/parent";
          dr:fieldnum 66;
        }
        }
      }
      augment "components/component/storage" {
        dr:fieldnum 167;
      }
      augment "components/component/storage/state" {
        dr:fieldnum 167;
        uses jnx-oc-platform:storage-info {
        augment "model" {
          dr:source "telemetryStorage/model";
          dr:fieldnum 53;
        }
        augment "description" {
          dr:source "telemetryStorage/description";
          dr:fieldnum 54;
        }
        augment "size" {
          dr:source "telemetryStorage/size";
          dr:fieldnum 55;
        }
        }
      }

      augment "components/component/name" {
        dr:source "oc_name";
        dr:fieldnum 51;
      }

      augment "components/component/state" {
        dr:fieldnum 151;
        uses jnx-oc-pf:component-state {
          augment "base-mac-address" {
            dr:source "telemetryChassisData/baseAddr";
            dr:fieldnum 69;
          }
          augment "base-num-mac-addresses" {
            dr:source "telemetryChassisData/numBaseAddr";
            dr:fieldnum 70;
          }
          augment "boot-time" {
            dr:source "telemetryFpcData/bootTime";
            dr:fieldnum 71;
          }
          augment "recent-reset-cause" {
            dr:source "telemetryFpcData/resetReason";
            dr:fieldnum 72;
          }
        }
      }

      augment "components/component/state/name" {
        dr:source "oc_name";
        dr:fieldnum 51;
      }
      augment "components/component/state/type" {
        dr:source "fruType";
        dr:fieldnum 52;
        dr:map CHASSIS          { dr:map-from 1 ; } // CHASSIS;
        dr:map BACKPLANE        { dr:map-from 2 ; } // BACKPLANE;
        dr:map FRU              { dr:map-from 3 ; } // FPM;
        dr:map POWER_SUPPLY     { dr:map-from 4 ; } // PDU;
        dr:map POWER_SUPPLY     { dr:map-from 5 ; } // PSM;
        dr:map FRU              { dr:map-from 6 ; } // CCG;
        dr:map CONTROLLER_CARD  { dr:map-from 7 ; } // RE;
        dr:map FRU              { dr:map-from 8 ; } // CB;
        dr:map LINECARD         { dr:map-from 9 ; } // FPC;
        dr:map FRU              { dr:map-from 10; } // PIC;
        dr:map LINECARD         { dr:map-from 11; } // SPMB;
        dr:map FABRIC           { dr:map-from 12; } // SIB;
        dr:map FRU              { dr:map-from 13; } // FTC; 
        dr:map FAN              { dr:map-from 14; } // FAN; 
        dr:map PORT             { dr:map-from 15; } // PORT; 
        dr:map FRU              { dr:map-from 16; } // MEZZ;
        dr:map LINECARD         { dr:map-from 17; } // FEB;
        dr:map SOFTWARE_MODULE  { dr:map-from 19; } // Software Module;
        dr:map BIOS             { dr:map-from 20; } // BIOS;
        dr:map BOOT_LOADER      { dr:map-from 21; } // BOOTLOADER;
        dr:map OPENCONFIG_HARDWARE_COMPONENT { dr:map-from 26; } // CIDX_STATIC_HW;
      }
      augment "components/component/state/id" {
        dr:source "serialNumber";
        dr:zero-suppressed;
        dr:fieldnum 53;
      }
      augment "components/component/state/description" {
        dr:source "description";
        dr:fieldnum 54;
      }
      augment "components/component/state/serial-no" {
        dr:source "serialNumber";
        dr:zero-suppressed;
        dr:fieldnum 55;
      }
      augment "components/component/state/part-no" {
        dr:source "partNumber";
        dr:zero-suppressed;
        dr:fieldnum 56;
      }
      augment "components/component/state/hardware-version" {
        dr:source "version";
        dr:zero-suppressed;
        dr:fieldnum 57;
      }
      augment "components/component/state/oper-status" {
        dr:source "state";
        dr:fieldnum 58;
        dr:map INACTIVE             { dr:map-from 3 ; } // Present
        dr:map ACTIVE               { dr:map-from 8 ; } // Online
        dr:map DISABLED             { dr:map-from 10; } // Offline
        dr:map DISABLED             { dr:map-from 12; } // Standby
        dr:map INACTIVE             { dr:map-from 14; } // Fault
        dr:map INACTIVE             { dr:map-from 15; } // Fault Power Off
        dr:map DISABLED             { dr:map-from 18; } // Power off
      }
      augment "components/component/state/location" {
        dr:source "location";
        dr:fieldnum 59;
      }
      augment "components/component/state/mfg-name" {
        dr:source "mfg_name";
        dr:zero-suppressed;
        dr:fieldnum 60;
      }
      augment "components/component/state/mfg-date" {
        dr:source "manufactureDate";
        dr:zero-suppressed;
        dr:fieldnum 61;
      }
      augment "components/component/state/firmware-version" {
        dr:source "firmware_version";
        dr:zero-suppressed;
        dr:fieldnum 62;
      }
      augment "components/component/state/software-version" {
        dr:source "software_version";
        dr:zero-suppressed;
        dr:fieldnum 63;
      }
      augment "components/component/state/removable" {
        dr:source "is_removable";
        dr:fieldnum 64;
      }
      augment "components/component/state/empty" {
        dr:source "empty";
        dr:fieldnum 65;
      }
      augment "components/component/state/parent" {
        dr:source "parent";
        dr:fieldnum 66;
      }
      augment "components/component/state/allocated-power" {
        dr:source "allocated_power";
        dr:fieldnum 67;
      }
      augment "components/component/state/used-power" {
        dr:source "used_power";
        dr:fieldnum 68;
      }
      augment "components/component/state/temperature" {
        dr:source "fruUtilization";
        dr:fieldnum 151;
      }
      augment "components/component/state/temperature/instant" {
        dr:source "temperature";
        dr:fieldnum 51;
      }
      augment "components/component/state/memory" {
        dr:source "fruUtilization";
        dr:fieldnum 152;
      }
      augment "components/component/state/memory/available" {
        dr:source "memory_dram_size";
        dr:fieldnum 51;
      }
      augment "components/component/state/memory/utilized" {
        dr:source "memory_dram_used";
        dr:fieldnum 52;
      }
      augment "components/component/properties" {
        dr:fieldnum 152;
      }
      augment "components/component/properties/property" {
        dr:source "propertyE";
        dr:fieldnum 151;
      }
      augment "components/component/properties/property/name" {
        dr:source "name";
        dr:fieldnum 51;
      }
      augment "components/component/properties/property/state" {
        dr:fieldnum 151;
      }
      augment "components/component/properties/property/state/value" {
        dr:source "value";
        dr:fieldnum 51;
      }
      augment "components/component/properties/property/state/configurable" {
        dr:source "configurable";
        dr:fieldnum 52;
      }
      augment "components/component/subcomponents" {
        dr:fieldnum 156;
      }
      augment "components/component/subcomponents/subcomponent" {
        dr:source "subcomponentE";
        dr:fieldnum 151;
      }
      augment "components/component/subcomponents/subcomponent/name" {
        dr:source "subcomp_name";
        dr:fieldnum 51;
      }
      augment "components/component/subcomponents/subcomponent/state" {
        dr:fieldnum 151;
      }
      augment "components/component/subcomponents/subcomponent/state/name" {
        dr:source "subcomp_name";
        dr:fieldnum 51;
      }

    }
  }

  notification "oc-fru-state-change" {
    dr:source-notification-name "hwd_module:fruE-event";
    uses oc-pf:platform-component-top {
      augment "components" {
        dr:source "/notification/hwd_module:fruE-event/evl_types:JunosOperState";
        dr:fieldnum 151;
      }
      augment "components/component" {
        dr:source "hwd_module:fruE";
        dr:fieldnum 151;
        uses oc-linecard:linecard-top {
            augment "linecard" {
               dr:fieldnum 161;
            }
            augment "linecard/state" {
                dr:fieldnum 151;
                uses jnx-oc-pf:linecard-info {
                   augment "boot-time" {
                        dr:source "telemetryFpcData/bootTime";
                        dr:zero-suppressed;
                        dr:fieldnum 51;
                   }
                   augment "recent-reset-cause" {
                       dr:source "telemetryFpcData/resetReason";
                       dr:zero-suppressed;
                       dr:fieldnum 52;
                   }
                }
            }
        }
      }
      augment "components/component/name" {
        dr:source "oc_name";
        dr:fieldnum 51;
      }
      augment "components/component/state" {
        dr:fieldnum 151;
        uses jnx-oc-pf:component-state {
          augment "boot-time" {
            dr:source "telemetryFpcData/bootTime";
            dr:fieldnum 71;
          }
          augment "recent-reset-cause" {
            dr:source "telemetryFpcData/resetReason";
            dr:fieldnum 72;
          }
        }
      }
      augment "components/component/state/type" {
        dr:source "fruType";
        dr:map CHASSIS          { dr:map-from 1 ; } // CHASSIS;
        dr:map BACKPLANE        { dr:map-from 2 ; } // BACKPLANE;
        dr:map FRU              { dr:map-from 3 ; } // FPM;
        dr:map POWER_SUPPLY     { dr:map-from 4 ; } // PDU;
        dr:map POWER_SUPPLY     { dr:map-from 5 ; } // PSM;
        dr:map FRU              { dr:map-from 6 ; } // CCG;
        dr:map CONTROLLER_CARD  { dr:map-from 7 ; } // RE;
        dr:map FRU              { dr:map-from 8 ; } // CB;
        dr:map LINECARD         { dr:map-from 9 ; } // FPC;
        dr:map FRU              { dr:map-from 10; } // PIC;
        dr:map LINECARD         { dr:map-from 11; } // SPMB;
        dr:map FABRIC           { dr:map-from 12; } // SIB;
        dr:map FRU              { dr:map-from 13; } // FTC;
        dr:map FAN              { dr:map-from 14; } // FAN;
        dr:map PORT             { dr:map-from 15; } // PORT;
        dr:map FRU              { dr:map-from 16; } // MEZZ;
        dr:map LINECARD         { dr:map-from 17; } // FEB;
        dr:map SOFTWARE_MODULE  { dr:map-from 19; } // Software Module;
        dr:map BIOS             { dr:map-from 20; } // BIOS;
        dr:map BOOT_LOADER      { dr:map-from 21; } // BOOTLOADER;
        dr:map OPENCONFIG_HARDWARE_COMPONENT { dr:map-from 26; } // CIDX_STATIC_HW;
        dr:fieldnum 52;
      }
      augment "components/component/state/id" {
        dr:source "serialNumber";
        dr:fieldnum 53;
      }
      augment "components/component/state/description" {
        dr:source "description";
        dr:fieldnum 54;
      }
      augment "components/component/state/serial-no" {
        dr:source "serialNumber";
        dr:fieldnum 55;
      }
      augment "components/component/state/part-no" {
        dr:source "partNumber";
        dr:fieldnum 56;
      }
      augment "components/component/state/hardware-version" {
        dr:source "version";
        dr:fieldnum 57;
      }
      augment "components/component/state/oper-status" {
        dr:source "state";
        dr:fieldnum 58;
        dr:map INACTIVE             { dr:map-from 3 ; } // Present
        dr:map ACTIVE               { dr:map-from 8 ; } // Online
        dr:map DISABLED             { dr:map-from 10; } // Offline
        dr:map DISABLED             { dr:map-from 12; } // Standby
        dr:map INACTIVE             { dr:map-from 14; } // Fault
        dr:map INACTIVE             { dr:map-from 15; } // Fault Power Off
        dr:map DISABLED             { dr:map-from 18; } // Power off
      }
      augment "components/component/state/location" {
        dr:source "location";
        dr:fieldnum 59;
      }
      augment "components/component/state/mfg-name" {
        dr:source "mfg_name";
        dr:fieldnum 60;
      }
      augment "components/component/state/mfg-date" {
        dr:source "manufactureDate";
        dr:fieldnum 61;
      }
      augment "components/component/state/firmware-version" {
        dr:source "firmware_version";
        dr:fieldnum 62;
      }
      augment "components/component/state/software-version" {
        dr:source "software_version";
        dr:fieldnum 63;
      }
      augment "components/component/state/removable" {
        dr:source "is_removable";
        dr:fieldnum 64;
      }
      augment "components/component/state/empty" {
        dr:source "empty";
        dr:fieldnum 65;
      }
      augment "components/component/state/parent" {
        dr:source "parent";
        dr:fieldnum 66;
      }
      augment "components/component/state/allocated-power" {
        dr:source "allocated_power";
        dr:fieldnum 67;
      }
      augment "components/component/state/temperature" {
        dr:source "fruUtilization";
        dr:fieldnum 151;
      }
      augment "components/component/state/temperature/instant" {
        dr:source "temperature";
        dr:fieldnum 51;
      }
      augment "components/component/state/memory" {
        dr:source "fruUtilization";
        dr:fieldnum 152;
      }
      augment "components/component/state/memory/available" {
        dr:source "memory_dram_size";
        dr:fieldnum 51;
      }
      augment "components/component/state/memory/utilized" {
        dr:source "memory_dram_used";
        dr:fieldnum 52;
      }
    }
  }

  notification "oc-subcomp-state-change" {
    dr:source-notification-name "hwd_module:subcomponentE-event";
    uses oc-pf:platform-component-top {
      augment "components" {
        dr:source "/notification/hwd_module:subcomponentE-event/evl_types:JunosOperState";
        dr:fieldnum 151;
      }
      augment "components/component" {
        dr:source "hwd_module:fruE";
        dr:fieldnum 151;
      }
      augment "components/component/name" {
        dr:source "oc_name";
        dr:fieldnum 51;
      }
      augment "components/component/subcomponents" {
        dr:fieldnum 156;
      }
      augment "components/component/subcomponents/subcomponent" {
        dr:source "subcomponentE";
        dr:fieldnum 151;
      }
      augment "components/component/subcomponents/subcomponent/name" {
        dr:source "subcomp_name";
        dr:fieldnum 51;
      }
      augment "components/component/subcomponents/subcomponent/state" {
        dr:fieldnum 151;
      }
      augment "components/component/subcomponents/subcomponent/state/name" {
        dr:source "subcomp_name";
        dr:fieldnum 51;
      }
    }
  }

  dr:command-app "hwdre";
  jnpr-proto:message-id "HWDRE-OC-MESSAGE-ID";
  dr:sub-component "re";

  rpc juniper-netconf-get {
    output {
        uses chassisd-inventory;
    }
  }
}
