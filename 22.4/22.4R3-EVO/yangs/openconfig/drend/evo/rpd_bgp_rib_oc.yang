/*
 * Render tree for BGP RIB Openconfig 
 *
 * November 2017, Lynne Morrison
 *
 * Copyright (c) 1998-2016, Juniper Networks, Inc.
 * All rights reserved.
 */

/**
 * @file
 * BGP RIB Render Tree. 
 */

module rpd_bgp_rib_oc {
  yang-version "1";

  // namespace
  namespace "http://juniper.net/yang/bgp_rib_oc_render";

  prefix "bgpriboc";

  import drend {
    prefix "dr";
  }
  import jnpr-proto { prefix jnpr-proto; }
  import jnx-aug-openconfig-bgp-rib { prefix jnx-oc-bgprib; }
  import openconfig-rib-bgp {prefix oc-bgprib; }


  description "
    Rendering Junos BGP routing table (RIB) in Openconfig BGP RIB Schema terms
  ";

  revision "2016-04-11" {
     description
      "OpenConfig public release";
    reference "0.2.0";
  }

  /*
   * Daemon that handles this hierarchy
   */
  dr:command-app "rpd";
  dr:sub-component "bgp-rib";
  jnpr-proto:message-id "RPD-BGP-RIB-OC-MESSAGE-ID";


  grouping rend-common-table-attrs {
    uses oc-bgprib:common-table-attrs {
      augment "num-routes" {
        dr:source "num-routes";
        dr:fieldnum 51;
      }
    }
  }

  grouping rend-routes-top {
    uses oc-bgprib:ipv4-routes {

      augment "routes" {
	dr:fieldnum 151;
      }
      augment "routes/route" {
        dr:source "route";
        dr:fieldnum 151;
      }
      augment "routes/route/prefix" {
        dr:source "prefix";
        dr:fieldnum 51;
      }
      augment "routes/route/attributes" {
	  dr:fieldnum 152;
      }
      augment "routes/route/attributes/origin" {
        dr:source "attributes-origin";
        dr:fieldnum 51;
      }
      augment "routes/route/attributes/as-path" {
        dr:source "attributes-as-path";
        dr:fieldnum 52;
      }
      augment "routes/route/attributes/as4-path" {
        dr:source "attributes-as4-path";
        dr:fieldnum 53;
      }
      augment "routes/route/attributes/next-hop" {
        dr:source "attributes-next-hop";
        dr:fieldnum 54;
      }
      augment "routes/route/attributes/med" {
        dr:source "attributes-med";
        dr:fieldnum 55;
      }
      augment "routes/route/attributes/local-pref" {
        dr:source "attributes-local-pref";
        dr:fieldnum 56;
      }
      augment "routes/route/attributes/atomic-aggr" {
        dr:source "attributes-atomic-aggr";
        dr:fieldnum 57;
      }
      augment "routes/route/attributes/aggregator" {
	  dr:fieldnum 151;
      }
      augment "routes/route/attributes/aggregator/as" {
        dr:source "attributes-aggregator-as";
        dr:fieldnum 58;
      }
      augment "routes/route/attributes/aggregator/as4" {
        dr:source "attributes-aggregator-as4";
        dr:fieldnum 59;
      }
      augment "routes/route/attributes/aggregator/address" {
        dr:source "attributes-aggregator-address";
        dr:fieldnum 60;
      }
      augment "routes/route/attributes/community" {
        dr:source "community";
        dr:fieldnum 152;
      }
      augment "routes/route/ext-attributes" {
	  dr:fieldnum 151;
      }
      augment "routes/route/ext-attributes/originator-id" {
        dr:source "ext-attributes-originator-id";
        dr:fieldnum 51;
      }
      augment "routes/route/ext-attributes/cluster-list" {
        dr:source "cluster-list";
        dr:fieldnum 52;
      }
      augment "routes/route/ext-attributes/ext-community" {
        dr:source "ext-community";
        dr:fieldnum 53;
      }
      augment "routes/route/ext-attributes/aigp" {
        dr:source "ext-attributes-aigp";
        dr:fieldnum 54;
      }
      augment "routes/route/ext-attributes/path-id" {
        dr:source "ext-attributes-path-id";
        dr:fieldnum 55;
      }
      augment "routes/route/ext-attributes/unknown-attribute" {
        dr:source "unknown-attributes";
        dr:fieldnum 151;
      }
      augment "routes/route/ext-attributes/unknown-attribute/attr-type" {
        dr:source "attr-type";
        dr:fieldnum 57;
      }
      augment "routes/route/ext-attributes/unknown-attribute/attr-len" {
        dr:source "attr-len";
        dr:fieldnum 58;
      }
      augment "routes/route/ext-attributes/unknown-attribute/attr-value" {
        dr:source "attr-val";
        dr:fieldnum 59;
      }
      augment "routes/route/last-modified-date" {
        dr:source "last-modified-date";
        dr:fieldnum 61;
      }
      augment "routes/route/last-update-received" {
        dr:source "last-update-received";
        dr:fieldnum 62;
      }
      augment "routes/route/valid-route" {
        dr:source "valid-route";
        dr:fieldnum 63;

      }
      augment "routes/route/invalid-reason" {
        dr:map INVALID_CLUSTER_LOOP { dr:map-from 3; }
        dr:map INVALID_AS_LOOP      { dr:map-from 5; }
        dr:map INVALID_ORIGINATOR   { dr:map-from 6; }
        dr:map INVALID_CONFED       { dr:map-from 4; }
        dr:source "invalid-reason";
        dr:fieldnum 64;
      }
      augment "routes/route/best-path" {
        dr:source "best-path";
        dr:fieldnum 65;
      }
    }
  }

  grouping rib-attr-top {
    uses oc-bgprib:common-route-attrs {

      augment "attributes" {
	  dr:fieldnum 152;
      }
      augment "attributes/origin" {
        dr:source "attributes-origin";
        dr:fieldnum 51;
      }
      augment "attributes/as-path" {
        dr:source "attributes-as-path";
        dr:fieldnum 52;
      }
      augment "attributes/as4-path" {
        dr:source "attributes-as4-path";
        dr:fieldnum 53;
      }
      augment "attributes/next-hop" {
        dr:source "attributes-next-hop";
        dr:fieldnum 54;
      }
      augment "attributes/med" {
        dr:source "attributes-med";
        dr:fieldnum 55;
      }
      augment "attributes/local-pref" {
        dr:source "attributes-local-pref";
        dr:fieldnum 56;
      }
      augment "attributes/atomic-aggr" {
        dr:source "attributes-atomic-aggr";
        dr:fieldnum 57;
      }
      augment "attributes/aggregator" {
	  dr:fieldnum 151;
      }
      augment "attributes/aggregator/as" {
        dr:source "attributes-aggregator-as";
        dr:fieldnum 58;
      }
      augment "attributes/aggregator/as4" {
        dr:source "attributes-aggregator-as4";
        dr:fieldnum 59;
      }
      augment "attributes/aggregator/address" {
        dr:source "attributes-aggregator-address";
        dr:fieldnum 60;
      }
      augment "attributes/community" {
        dr:source "community";
        dr:fieldnum 152;
      }
      augment "ext-attributes" {
	  dr:fieldnum 151;
      }
      augment "ext-attributes/originator-id" {
        dr:source "ext-attributes-originator-id";
        dr:fieldnum 51;
      }
      augment "ext-attributes/cluster-list" {
        dr:source "cluster-list";
        dr:fieldnum 52;
      }
      augment "ext-attributes/ext-community" {
        dr:source "ext-community";
        dr:fieldnum 53;
      }
      augment "ext-attributes/aigp" {
        dr:source "ext-attributes-aigp";
        dr:fieldnum 54;
      }
      augment "ext-attributes/path-id" {
        dr:source "ext-attributes-path-id";
        dr:fieldnum 55;
      }
      augment "ext-attributes/unknown-attribute" {
        dr:source "unknown-attributes";
        dr:fieldnum 151;
      }
      augment "ext-attributes/unknown-attribute/attr-type" {
        dr:source "attr-type";
        dr:fieldnum 57;
      }
      augment "ext-attributes/unknown-attribute/attr-len" {
        dr:source "attr-len";
        dr:fieldnum 58;
      }
      augment "ext-attributes/unknown-attribute/attr-value" {
        dr:source "attr-val";
        dr:fieldnum 59;
      }
      augment "last-modified-date" {
        dr:source "last-modified-date";
        dr:fieldnum 61;
      }
      augment "last-update-received" {
        dr:source "last-update-received";
        dr:fieldnum 62;
      }
      augment "valid-route" {
        dr:source "valid-route";
        dr:fieldnum 63;

      }
      augment "invalid-reason" {
        dr:map INVALID_CLUSTER_LOOP { dr:map-from 3; }
        dr:map INVALID_AS_LOOP      { dr:map-from 5; }
        dr:map INVALID_ORIGINATOR   { dr:map-from 6; }
        dr:map INVALID_CONFED       { dr:map-from 4; }
        dr:source "invalid-reason";
        dr:fieldnum 64;
      }
      augment "best-path" {
        dr:source "best-path";
        dr:fieldnum 65;
      }
    }
  }

  grouping notif-routes-top {
    container routes {
      dr:fieldnum 151;
      list route {
        dr:source "route";
        dr:fieldnum 151;
        dr:atomic-data;
        key "prefix path-id";
        uses jnx-oc-bgprib:route-jnx-rtkey {
          augment "prefix" {
            dr:source "prefix";
            dr:fieldnum 51;
          }
          augment "path-id" {
            dr:source "ext-attributes-path-id";
            dr:fieldnum 52;
          }
        }
        uses rib-attr-top;
      }
    }
  }

  rpc juniper-netconf-get {
    dr:command-top-of-output "/oc-bgp-rib-information";
    dr:command-full-name "request drend juniper-netconf-get";
    dr:command-help "Default <get> rpc";

    output {
      container bgp-rib {
        dr:source "/bgp-rib";
        dr:fieldnum 66;
        dr:source-notification-name "bgp-loc-rib-ipv4" ;
        dr:source-notification-name "bgp-rib-in-pre-ipv4" ;
        dr:source-notification-name "bgp-rib-in-post-ipv4" ;
        dr:source-notification-name "bgp-rib-out-pre-ipv4" ;
        dr:source-notification-name "bgp-rib-out-post-ipv4" ;
        dr:source-notification-name "bgp-loc-rib-ipv6" ;
        dr:source-notification-name "bgp-rib-in-pre-ipv6" ;
        dr:source-notification-name "bgp-rib-in-post-ipv6" ;
        dr:source-notification-name "bgp-rib-out-pre-ipv6" ;
        dr:source-notification-name "bgp-rib-out-post-ipv6" ;
        container afi-safis {
	  dr:fieldnum 151;
          list afi-safi {
           key "afi-safi-name";
	   dr:source "nlri";
	   dr:fieldnum 151;

             leaf afi-safi-name {
               type string;
               dr:source "rib-name";
               dr:fieldnum 52;
               dr:map IPV4_UNICAST {dr:map-from inet.0; }
               dr:map IPV6_UNICAST {dr:map-from inet6.0; }
             }
             dr:source-notification-name "bgp-loc-rib-ipv4" ;
             dr:source-notification-name "bgp-rib-in-pre-ipv4" ;
             dr:source-notification-name "bgp-rib-in-post-ipv4" ;
             dr:source-notification-name "bgp-rib-out-pre-ipv4" ;
             dr:source-notification-name "bgp-rib-out-post-ipv4" ;
             dr:source-notification-name "bgp-loc-rib-ipv6" ;
             dr:source-notification-name "bgp-rib-in-pre-ipv6" ;
             dr:source-notification-name "bgp-rib-in-post-ipv6" ;
             dr:source-notification-name "bgp-rib-out-pre-ipv6" ;
             dr:source-notification-name "bgp-rib-out-post-ipv6" ;
	     container ipv4-unicast {
	       when "/bgp-rib/ipv4-unicast/afi-safi-name[name='IPV4_UNICAST']";
	       dr:source "ipv4-unicast";
	       dr:fieldnum 151;
               dr:source-notification-name "bgp-loc-rib-ipv4" ;
               dr:source-notification-name "bgp-rib-in-pre-ipv4" ;
               dr:source-notification-name "bgp-rib-in-post-ipv4" ;
               dr:source-notification-name "bgp-rib-out-pre-ipv4" ;
               dr:source-notification-name "bgp-rib-out-post-ipv4" ;
	       container loc-rib {
                 dr:source "local-rib";
		 dr:fieldnum 151;
                 dr:source-notification-name "bgp-loc-rib-ipv4" ;
	         uses rend-common-table-attrs;
                 uses notif-routes-top;
               }

	       container neighbors {
		 dr:fieldnum 152;
                 list neighbor {
	           key "neighbor-address";
                   dr:source "neighbor";
                   dr:fieldnum 151;
                   leaf neighbor-address {
                     type string;
                     dr:source "neighbor-address";
                     dr:fieldnum 52;
                   }
                   dr:source-notification-name "bgp-rib-in-pre-ipv4" ;
                   dr:source-notification-name "bgp-rib-in-post-ipv4" ;
                   dr:source-notification-name "bgp-rib-out-pre-ipv4" ;
                   dr:source-notification-name "bgp-rib-out-post-ipv4" ;
                   container adj-rib-in-pre {
                     dr:source "adj-rib-in-pre";
                     dr:fieldnum 151;
                     dr:source-notification-name "bgp-rib-in-pre-ipv4";
                     uses rend-common-table-attrs;
                     uses notif-routes-top;
                   }

                   container adj-rib-in-post {
                     dr:source "adj-rib-in-post";
                     dr:fieldnum 152;
                     dr:source-notification-name "bgp-rib-in-post-ipv4";
                     uses rend-common-table-attrs;
                     uses notif-routes-top;
                   }

                   container adj-rib-out-pre {
                     dr:source "adj-rib-out-pre";
                     dr:fieldnum 153;
                     dr:source-notification-name "bgp-rib-out-pre-ipv4";
                     uses rend-common-table-attrs;
                     uses notif-routes-top;
                   }

                   container adj-rib-out-post {
                     dr:source "adj-rib-out-post";
                     dr:fieldnum 154;
                     dr:source-notification-name "bgp-rib-out-post-ipv4";
                     uses rend-common-table-attrs;
                     uses notif-routes-top;
                   }
                 }
               }
             }

	     container ipv6-unicast {
	       when "/bgp-rib/ipv6-unicast/afi-safi-name[name='IPV6_UNICAST']";
	       dr:source "ipv6-unicast";
	       dr:fieldnum 153;
               dr:source-notification-name "bgp-loc-rib-ipv6" ;
               dr:source-notification-name "bgp-rib-in-pre-ipv6" ;
               dr:source-notification-name "bgp-rib-in-post-ipv6" ;
               dr:source-notification-name "bgp-rib-out-pre-ipv6" ;
               dr:source-notification-name "bgp-rib-out-post-ipv6" ;
	       container loc-rib {
                 dr:source "local-rib";
                 dr:fieldnum 151;
                 dr:source-notification-name "bgp-loc-rib-ipv6";
	         uses rend-common-table-attrs;
                 uses notif-routes-top;
               }

	       container neighbors {
		 dr:fieldnum 152;
                 list neighbor {
	           key neighbor-address;
                   dr:source "neighbor";
                   dr:fieldnum 152;
                   leaf neighbor-address {
                     type string;
                     dr:source "neighbor-address";
                     dr:fieldnum 52;
                   }
                   dr:source-notification-name "bgp-rib-in-pre-ipv6" ;
                   dr:source-notification-name "bgp-rib-in-post-ipv6" ;
                   dr:source-notification-name "bgp-rib-out-pre-ipv6" ;
                   dr:source-notification-name "bgp-rib-out-post-ipv6" ;
                   container adj-rib-in-pre {
                     dr:source "adj-rib-in-pre";
                     dr:fieldnum 151;
                     dr:source-notification-name "bgp-rib-in-pre-ipv6";
                     uses rend-common-table-attrs;
                     uses notif-routes-top;
                   }

                   container adj-rib-in-post {
                     dr:source "adj-rib-in-post";
                     dr:fieldnum 152;
                     dr:source-notification-name "bgp-rib-in-post-ipv6";
                     uses rend-common-table-attrs;
                     uses notif-routes-top;
                   }

                   container adj-rib-out-pre {
                     dr:source "adj-rib-out-pre";
                     dr:fieldnum 153;
                     dr:source-notification-name "bgp-rib-out-pre-ipv6";
                     uses rend-common-table-attrs;
                     uses notif-routes-top;
                   }

                   container adj-rib-out-post {
                     dr:source "adj-rib-out-post";
                     dr:fieldnum 154;
                     dr:source-notification-name "bgp-rib-out-post-ipv6";
                     uses rend-common-table-attrs;
                     uses notif-routes-top;
                   }
                 }
               }
             }
           }
         }
       }
     }
   }

   notification oc-bgp-loc-rib-ipv4 {
     dr:source-notification-name "bgp-loc-rib-ipv4";
     container bgp-rib {
       dr:source "/notification/bgp-loc-rib-ipv4/bgp-rib/";
       dr:fieldnum 66;
       container afi-safis {
         dr:fieldnum 151;
         list afi-safi {
           key "afi-safi-name";
           dr:source "nlri";
           dr:fieldnum 151;
           leaf afi-safi-name {
             type string;
             dr:source "rib-name";
             dr:fieldnum 52;
             dr:map IPV4_UNICAST {dr:map-from inet.0; }
             dr:map IPV6_UNICAST {dr:map-from inet6.0; }
           }

           container ipv4-unicast {
             when "/notification/oc-bgp-loc-rib-ipv4/bgp-rib/ipv4-unicast/afi-safi-name[name='IPV4_UNICAST']";
             dr:source "ipv4-unicast";
             dr:fieldnum 151;
             container loc-rib {
               dr:source "local-rib";
               dr:fieldnum 151;
               uses notif-routes-top;
             }
           }
         }
       }
     }
   }

   notification oc-bgp-rib-in-pre-ipv4 {
     dr:source-notification-name "bgp-rib-in-pre-ipv4";
     container bgp-rib {
       dr:source "/notification/bgp-rib-in-pre-ipv4/bgp-rib";
       dr:fieldnum 66;
       container afi-safis {
         dr:fieldnum 151;
         list afi-safi {
           key "afi-safi-name";
           dr:source "nlri";
           dr:fieldnum 151;
           leaf afi-safi-name {
             type string;
             dr:source "rib-name";
             dr:fieldnum 52;
             dr:map IPV4_UNICAST {dr:map-from inet.0; }
             dr:map IPV6_UNICAST {dr:map-from inet6.0; }
           }
           container ipv4-unicast {
             when "/notification/oc-bgp-rib-in-pre-ipv4/bgp-rib/ipv4-unicast/afi-safi-name[name='IPV4_UNICAST']";
             dr:source "ipv4-unicast";
             dr:fieldnum 151;
             container neighbors {
               dr:fieldnum 152;
               list neighbor {
                 key "neighbor-address";
                 dr:source "neighbor";
                 dr:fieldnum 151;
                 leaf neighbor-address {
                   type string;
                   dr:source "neighbor-address";
                   dr:fieldnum 52;
                 }
                 container adj-rib-in-pre {
                   dr:source "adj-rib-in-pre";
                   dr:fieldnum 151;
                   uses notif-routes-top;
                 }
               }
             }
           }
         }
       }
     }
   }

   notification oc-bgp-rib-in-post-ipv4 {
     dr:source-notification-name "bgp-rib-in-post-ipv4";
     container bgp-rib {
       dr:source "/notification/bgp-rib-in-post-ipv4/bgp-rib";
       dr:fieldnum 66;
       container afi-safis {
         dr:fieldnum 151;
         list afi-safi {
           key "afi-safi-name";
           dr:source "nlri";
           dr:fieldnum 151;
           leaf afi-safi-name {
             type string;
             dr:source "rib-name";
             dr:fieldnum 52;
             dr:map IPV4_UNICAST {dr:map-from inet.0; }
             dr:map IPV6_UNICAST {dr:map-from inet6.0; }
           }
           container ipv4-unicast {
             when "/notification/oc-bgp-rib-in-post-ipv4/bgp-rib/ipv4-unicast/afi-safi-name[name='IPV4_UNICAST']";
             dr:source "ipv4-unicast";
             dr:fieldnum 151;
             container neighbors {
               dr:fieldnum 152;
               list neighbor {
                 key "neighbor-address";
                 dr:source "neighbor";
                 dr:fieldnum 151;
                 leaf neighbor-address {
                   type string;
                   dr:source "neighbor-address";
                   dr:fieldnum 52;
                 }
                 container adj-rib-in-post {
                   dr:source "adj-rib-in-post";
                   dr:fieldnum 152;
                   uses notif-routes-top;
                 }
               }
             }
           }
         }
       }
     }
   }

   notification oc-bgp-rib-out-pre-ipv4 {
     dr:source-notification-name "bgp-rib-out-pre-ipv4";
     container bgp-rib {
       dr:source "/notification/bgp-rib-out-pre-ipv4/bgp-rib";
       dr:fieldnum 66;
       container afi-safis {
         dr:fieldnum 151;
         list afi-safi {
           key "afi-safi-name";
           dr:source "nlri";
           dr:fieldnum 151;
           leaf afi-safi-name {
             type string;
             dr:source "rib-name";
             dr:fieldnum 52;
             dr:map IPV4_UNICAST {dr:map-from inet.0; }
             dr:map IPV6_UNICAST {dr:map-from inet6.0; }
           }
           container ipv4-unicast {
             when "/notification/oc-bgp-rib-out-pre-ipv4/bgp-rib/ipv4-unicast/afi-safi-name[name='IPV4_UNICAST']";
             dr:source "ipv4-unicast";
             dr:fieldnum 151;
             container neighbors {
               dr:fieldnum 152;
               list neighbor {
                 key "neighbor-address";
                 dr:source "neighbor";
                 dr:fieldnum 151;
                 leaf neighbor-address {
                   type string;
                   dr:source "neighbor-address";
                   dr:fieldnum 52;
                 }
                 container adj-rib-out-pre {
                   dr:source "adj-rib-out-pre";
                   dr:fieldnum 153;
                   uses notif-routes-top;
                 }
               }
             }
           }
         }
       }
     }
   }

   notification oc-bgp-rib-out-post-ipv4 {
     dr:source-notification-name "bgp-rib-out-post-ipv4";
     container bgp-rib {
       dr:source "/notification/bgp-rib-out-post-ipv4/bgp-rib";
       dr:fieldnum 66;
       container afi-safis {
         dr:fieldnum 151;
         list afi-safi {
           key "afi-safi-name";
           dr:source "nlri";
           dr:fieldnum 151;
           leaf afi-safi-name {
             type string;
             dr:source "rib-name";
             dr:fieldnum 52;
             dr:map IPV4_UNICAST {dr:map-from inet.0; }
             dr:map IPV6_UNICAST {dr:map-from inet6.0; }
           }
           container ipv4-unicast {
             when "/notification/oc-bgp-rib-out-post-ipv4/bgp-rib/ipv4-unicast/afi-safi-name[name='IPV4_UNICAST']";
             dr:source "ipv4-unicast";
             dr:fieldnum 151;
             container neighbors {
               dr:fieldnum 152;
               list neighbor {
                 key "neighbor-address";
                 dr:source "neighbor";
                 dr:fieldnum 151;
                 leaf neighbor-address {
                   type string;
                   dr:source "neighbor-address";
                   dr:fieldnum 52;
                 }
                 container adj-rib-out-post {
                   dr:source "adj-rib-out-post";
                   dr:fieldnum 154;
                   uses notif-routes-top;
                 }
               }
             }
           }
         }
       }
     }
   }
   /*IPV6 Notification
    */
   notification oc-bgp-loc-rib-ipv6 {
     dr:source-notification-name "bgp-loc-rib-ipv6";
     container bgp-rib {
       dr:source "/notification/bgp-loc-rib-ipv6/bgp-rib/";
       dr:fieldnum 66;
       container afi-safis {
         dr:fieldnum 151;
         list afi-safi {
           key "afi-safi-name";
           dr:source "nlri";
           dr:fieldnum 151;
           leaf afi-safi-name {
             type string;
             dr:source "rib-name";
             dr:fieldnum 52;
             dr:map IPV4_UNICAST {dr:map-from inet.0; }
             dr:map IPV6_UNICAST {dr:map-from inet6.0; }
           }
           container ipv6-unicast {
             when "/notification/oc-bgp-loc-rib-ipv6/bgp-rib/ipv6-unicast/afi-safi-name[name='IPV6_UNICAST']";
             dr:source "ipv6-unicast";
             dr:fieldnum 153;
             container loc-rib {
               dr:source "local-rib";
               dr:fieldnum 151;
               uses notif-routes-top;
             }
           }
         }
       }
     }
   }

   notification oc-bgp-rib-in-pre-ipv6 {
     dr:source-notification-name "bgp-rib-in-pre-ipv6";
     container bgp-rib {
       dr:source "/notification/bgp-rib-in-pre-ipv6/bgp-rib";
       dr:fieldnum 66;
       container afi-safis {
         dr:fieldnum 151;
         list afi-safi {
           key "afi-safi-name";
           dr:source "nlri";
           dr:fieldnum 151;
           leaf afi-safi-name {
             type string;
             dr:source "rib-name";
             dr:fieldnum 52;
             dr:map IPV4_UNICAST {dr:map-from inet.0; }
             dr:map IPV6_UNICAST {dr:map-from inet6.0; }
           }
           container ipv6-unicast {
             when "/notification/oc-bgp-rib-in-pre-ipv6/bgp-rib/ipv6-unicast/afi-safi-name[name='IPV6_UNICAST']";
             dr:source "ipv6-unicast";
             dr:fieldnum 153;
             container neighbors {
               dr:fieldnum 152;
               list neighbor {
                 key "neighbor-address";
                 dr:source "neighbor";
                 dr:fieldnum 152;
                 leaf neighbor-address {
                   type string;
                   dr:source "neighbor-address";
                   dr:fieldnum 52;
                 }
                 container adj-rib-in-pre {
                   dr:source "adj-rib-in-pre";
                   dr:fieldnum 151;
                   uses notif-routes-top;
                 }
               }
             }
           }
         }
       }
     }
   }

   notification oc-bgp-rib-in-post-ipv6 {
     dr:source-notification-name "bgp-rib-in-post-ipv6";
     container bgp-rib {
       dr:source "/notification/bgp-rib-in-post-ipv6/bgp-rib";
       dr:fieldnum 66;
       container afi-safis {
         dr:fieldnum 151;
         list afi-safi {
           key "afi-safi-name";
           dr:source "nlri";
           dr:fieldnum 151;
           leaf afi-safi-name {
             type string;
             dr:source "rib-name";
             dr:fieldnum 52;
             dr:map IPV4_UNICAST {dr:map-from inet.0; }
             dr:map IPV6_UNICAST {dr:map-from inet6.0; }
           }
           container ipv6-unicast {
             when "/notification/oc-bgp-rib-in-post-ipv6/bgp-rib/ipv6-unicast/afi-safi-name[name='IPV6_UNICAST']";
             dr:source "ipv6-unicast";
             dr:fieldnum 153;
             container neighbors {
               dr:fieldnum 152;
               list neighbor {
                 key "neighbor-address";
                 dr:source "neighbor";
                 dr:fieldnum 152;
                 leaf neighbor-address {
                   type string;
                   dr:source "neighbor-address";
                   dr:fieldnum 52;
                 }
                 container adj-rib-in-post {
                   dr:source "adj-rib-in-post";
                   dr:fieldnum 152;
                   uses notif-routes-top;
                 }
               }
             }
           }
         }
       }
     }
   }

   notification oc-bgp-rib-out-pre-ipv6 {
     dr:source-notification-name "bgp-rib-out-pre-ipv6";
     container bgp-rib {
       dr:source "/notification/bgp-rib-out-pre-ipv6/bgp-rib";
       dr:fieldnum 66;
       container afi-safis {
         dr:fieldnum 151;
         list afi-safi {
           key "afi-safi-name";
           dr:source "nlri";
           dr:fieldnum 151;
           leaf afi-safi-name {
             type string;
             dr:source "rib-name";
             dr:fieldnum 52;
             dr:map IPV4_UNICAST {dr:map-from inet.0; }
             dr:map IPV6_UNICAST {dr:map-from inet6.0; }
           }
           container ipv6-unicast {
             when "/notification/oc-bgp-rib-out-pre-ipv6/bgp-rib/ipv6-unicast/afi-safi-name[name='IPV6_UNICAST']";
             dr:source "ipv6-unicast";
             dr:fieldnum 153;
             container neighbors {
               dr:fieldnum 152;
               list neighbor {
                 key "neighbor-address";
                 dr:source "neighbor";
                 dr:fieldnum 152;
                 leaf neighbor-address {
                   type string;
                   dr:source "neighbor-address";
                   dr:fieldnum 52;
                 }
                 container adj-rib-out-pre {
                   dr:source "adj-rib-out-pre";
                   dr:fieldnum 153;
                   uses notif-routes-top;
                 }
               }
             }
           }
         }
       }
     }
   }

   notification oc-bgp-rib-out-post-ipv6 {
     dr:source-notification-name "bgp-rib-out-post-ipv6";
     container bgp-rib {
       dr:source "/notification/bgp-rib-out-post-ipv6/bgp-rib";
       dr:fieldnum 66;
       container afi-safis {
         dr:fieldnum 151;
         list afi-safi {
           key "afi-safi-name";
           dr:source "nlri";
           dr:fieldnum 151;
           leaf afi-safi-name {
             type string;
             dr:source "rib-name";
             dr:fieldnum 52;
             dr:map IPV4_UNICAST {dr:map-from inet.0; }
             dr:map IPV6_UNICAST {dr:map-from inet6.0; }
           }
           container ipv6-unicast {
             when "/notification/oc-bgp-rib-out-post-ipv6/bgp-rib/ipv6-unicast/afi-safi-name[name='IPV6_UNICAST']";
             dr:source "ipv6-unicast";
             dr:fieldnum 153;
             container neighbors {
               dr:fieldnum 152;
               list neighbor {
                 key "neighbor-address";
                 dr:source "neighbor";
                 dr:fieldnum 152;
                 leaf neighbor-address {
                   type string;
                   dr:source "neighbor-address";
                   dr:fieldnum 52;
                 }
                 container adj-rib-out-post {
                   dr:source "adj-rib-out-post";
                   dr:fieldnum 154;
                   uses notif-routes-top;
                 }
               }
             }
           }
         }
       }
     }
   }
}
