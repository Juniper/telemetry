module rpd_ni_evpn_render {
  yang-version 1;

  namespace "http://juniper.net/yang/rpd_ni_evpn_render";

  prefix "evpn";

  import drend {
    prefix "dr";
  }
  import jnpr-proto { prefix jnpr-proto; }
  import openconfig-yang-types { prefix yang; }

  description "
    Rendering Junos evpn State in juniper evpn Schema terms
  ";
  revision "2019-04-02" {
    description "Updated to OC evpn yang v0.0.1"; 
  }


  grouping rend-evpn-instance-info {
    leaf label-allocation-mode { 
      type string; 
      dr:source label-allocation-mode;
      dr:fieldnum 70;
    }
  }
 
  grouping rend-evpn-instance-statistics {
     leaf num-peers         { 
       type uint16; 
       dr:source "num-peers";
       dr:fieldnum 51;
     }

     leaf num-interfaces    {
       type uint32; 
       dr:source "num-interfaces";
       dr:fieldnum 52;
       description "Number of local interfaces";
     }
     leaf num-interfaces-up { 
       type uint32; 
       dr:source "num-interfaces-up";
       dr:fieldnum 53;
       description "Number of local interfaces with status UP";
     }

     leaf num-irb-interfaces    { 
       type uint16; 
       dr:source "num-irb-interfaces";
       dr:fieldnum 54;
       description "Number of irb interfaces";
     }
     leaf num-irb-interfaces-up { 
       type uint16; 
       dr:source "num-irb-interfaces-up";
       dr:fieldnum 55;
       description "Number of irb interfaces with status UP";
     }

     leaf num-remote-macs      { 
       type uint32; 
       dr:source "num-remote-macs";
       dr:fieldnum 59;
       description "Number of macs learned from remote peers";
     }
     leaf num-remote-mac-ip-v4   { 
       type uint32; 
       dr:source "num-remote-mac-ip-v4";
       dr:fieldnum 60;
       description "Number of ipv4 macs-ip routes learned from remote peers";
     }
     leaf num-remote-mac-ip-v6   { 
       type uint32; 
       dr:source "num-remote-mac-ip-v6";
       dr:fieldnum 61;
       description "Number of ipv6 macs-ip routes learned from remote peers";
     }

     leaf num-remote-irb-macs  { 
       type uint32; 
       dr:source "num-remote-irb-macs";
       dr:fieldnum 62;
       description "Number of irb macs learned from remote peers";
     }

     leaf num-ethernet-segments { 
       type uint32; 
       dr:source "num-ethernet-segments";
       dr:fieldnum 63;
       description "Number of ethernet-segment routes received from remote peers";
     }

     uses rend-evpn-instance-info;
   }

  grouping rend-interface-group {
    leaf name { 
      type string; 
       dr:source "name";
       dr:fieldnum 61;
       description "Interface name";
    }
    leaf esi  { 
      type string; 
      dr:source "esi";
      dr:fieldnum 62;
      description "Ethernet Segment Interface";
    }
    leaf mode { 
      type string; 
      dr:source "mode";
      dr:fieldnum 63;
      description "Multihoming mode";
    }
    leaf status { 
      type string; 
      dr:source "status";
      dr:fieldnum 64;
      description "Resolution status";
    }
  }

 grouping rend-irb-interface-group {
   leaf name {
     type string; 
     dr:source "name";
     dr:fieldnum 61;
     description "IRB Interface name";
   }
   leaf virtual-gateway-esi {
     type string;
     dr:source "virtual-gateway-esi";
     dr:fieldnum 62;
     description "Virtual Gateway ESI";
   }
   leaf status { 
     type string; 
     dr:source "status";
     dr:fieldnum 63;
     description "Status";
   }
   leaf l3-context {
     type string;
     dr:source "l3-context";
     dr:fieldnum 64;
     description "L3 context name";
   }
 }

  grouping rend-peer-group {
    leaf peer-address   { 
      type string; 
      dr:source "peer-address";
      dr:fieldnum 71;
      description "Peer address";
    }
    leaf num-auto-discovery-routes  { 
      type uint32; 
      dr:source "num-auto-discovery-routes";
      dr:fieldnum 73;
      description "Number of auto-discovery i.e Type 1 routes received from peer";
    }
    leaf num-multicast-routes  { 
      type uint32; 
      dr:source "num-multicast-routes";
      dr:fieldnum 74;
      description "Number of multicast i.e Type 3 routes received from peer";
    }
    leaf num-ethernet-segment-routes   { 
      type uint32; 
      dr:source "num-ethernet-segment-routes";
      dr:fieldnum 75;
      description "Number of ethernet-segment routes i.e Type 4 routes received from peer";
    }
    leaf num-mac-routes { 
      type uint32; 
      dr:source "num-mac-routes";
      dr:fieldnum 76;
      description "Number of Type 2 MAC routes received from peer";
    }
    leaf num-mac-ip-routes { 
      type uint32; 
      dr:source "num-mac-ip-routes";
      dr:fieldnum 77;
      description "Number of Type 2 MAC+IP routes received from peer";
    }
    leaf num-selective-multicast-routes { 
      type uint32; 
      dr:source "num-selective-multicast-routes";
      dr:fieldnum 78;
      description "Number of selective multicast i.e Type 6 routes received from peer";
    }
  }

  grouping remote-pe-group {
    leaf ip-address {
      type string;
      dr:source "ip-address";
      dr:fieldnum 71;
      description "Remote peer address";
    }
    leaf mode {
      type string;
      dr:source "mode";
      dr:fieldnum 72;
      description "Multihoming Mode";
    }
  }

  grouping esi-remote-pe-group {
    list remote-pe {
      description "Remote peers";
      key "ip-address";
      dr:source "remote-pe";
      dr:fieldnum 151;
      uses remote-pe-group;
    }
  }

  grouping esi-df-group {
    leaf df-election-algorithm {
      type string;
      dr:source "df-election-algorithm";
      dr:fieldnum 75;
      description "Designated forwarder algorithm in use";
    }
    leaf designated-forwarder {
      type string;
      dr:source-notification-name "change-designated-forwarder";
      dr:source "designated-forwarder";
      dr:fieldnum 76;
      description "Elected designated forwarder address";
    }
  }

  grouping esi-local-intf-group {
    leaf local-intf-name {
      type string;
      dr:source "local-intf-name";
      dr:fieldnum 73;
      description "ethernet segment interface name";
    }
    leaf local-intf-status {
      type string;
      dr:source "local-intf-status";
      dr:fieldnum 74;
      description "ethernet segment interface status";
    }
  }


/* IGMP/MLD snooping database  */

  grouping sgdb-esi-group  {
    leaf esi {
      type string;
      dr:source "esi";
      dr:fieldnum 152;
      description "Ethernet Segment Interface";
    }

    leaf local-intf-name {
      type string;
      dr:source "local-intf-name";
      dr:fieldnum 151;
      description "Interface name";
    }

    leaf join-sync-status {
      type string;
      dr:source "join-sync-status";
      dr:fieldnum 153;
      description "Join sync route Type 7 status";
    }

    leaf join-sync-last-updated {
      type yang:date-and-time;
      dr:source "join-sync-last-updated";
      dr:fieldnum 154;
      description "Join sync route Type 7 last status change time";
    }

    leaf leave-sync-status {
      type string;
      dr:source "leave-sync-status";
      dr:fieldnum 155;
      description "Leave sync route Type 8 status";
    }

    leaf leave-sync-last-updated {
      type yang:date-and-time;
      dr:source "leave-sync-last-updated";
      dr:fieldnum 156;
      description "Leave sync route Type 8 last status change time";
    }

  }

  grouping rend-sgdb-esi-group  {
    list sgdb-esi {
      description "Multicast source group database esi list";
      key "esi";
      dr:source "sgdb-esi";
      dr:fieldnum 151;
      uses sgdb-esi-group;
    }
  }


  grouping rend-sgdb-group {
    leaf ethernet-tag-id {
      type uint32;
      dr:source "l2-domain-id";
      dr:fieldnum 71;
      description "Ethernet tag identifier VNI value";
    }
    leaf group  {
      type string;
      dr:source "group";
      dr:fieldnum 72;
      description "Multicast group address";
    }
    leaf source {
      type string;
      dr:source "source";
      dr:fieldnum 73;
      description "Multicast source address";
    }
    leaf total-esi-fanout {
      type uint32;
      dr:source "total-esi-fanout";
      dr:fieldnum 74;
      description "Number of ESI interested in the multicast group";
    }
    leaf total-local-fanout {
      type uint32;
      dr:source "total-local-fanout";
      dr:fieldnum 75;
      description "Number of local interface interested in the multicast group";
    }
    leaf total-remote-fanout {
      type uint32;
      dr:source "total-remote-fanout";
      dr:fieldnum 76;
      description "Number of remote peers interested in the multicast group";
    }

    uses rend-sgdb-esi-group;
  }


  grouping rend-ethernet-segment-group {
    leaf esi {
      type string;
      dr:source "esi";
      dr:fieldnum 71;
      description "Ethernet segment interface";
    }
    leaf status {
      type string;
      dr:source "status";
      dr:fieldnum 72;
      description "Status";
    }
    uses esi-local-intf-group;
    uses esi-df-group;
    uses esi-remote-pe-group;
  }


  grouping ar-nexthops {
    leaf nexthop-index {
      type uint32; 
      dr:source "nexthop-index";
      dr:fieldnum 72;
      description "Nexthop index value";
    }
    leaf vni-id {
      type uint32; 
      dr:source "vni-id";
      dr:fieldnum 71;
      description "Virtual network identifier";
    }
    leaf interface {
      type string; 
      dr:source "interface";
      dr:fieldnum 73;
      description "Interface name";
    }
    leaf replicator-ip {
      type string; 
      dr:source "replicator-ip";
      dr:fieldnum 74;
      description "Replicator peer address value";
    }
    leaf is-designated-node {
      type boolean; 
      dr:source "is-designated-node";
      dr:fieldnum 75;
      description "True if replicator is designated forwarder";
    }
  }

  grouping rend-ar-nexthops {
    list nexthops {
      description "Nexthops";
      key "nexthop-index";
      dr:source "nexthops";
      dr:fieldnum 171;
      uses ar-nexthops;
    }
  }

  grouping rend-ar-l2-domain {
      list l2-domain {
        description "L2 domains";
        key "vni-id";
        dr:source "l2-domain";
        dr:fieldnum 171;

        leaf vni-id {
          dr:source "vni-id";
          type uint32; 
          dr:fieldnum 51;
          description "Virtual network identifier";
        }
        uses rend-ar-nexthops;
      }
  }
  grouping rend-assisted-replication {
    leaf role {
      dr:source "role";
      type string; 
      dr:fieldnum 51;
      description "Assisted replication role leaf or replicator";
    }
    uses rend-ar-l2-domain; 
  }

  dr:command-app "rpd";
  dr:sub-component "evpn";
  jnpr-proto:message-id "RPD-NI-EVPN-OC-MESSAGE-ID";

  rpc juniper-netconf-get {
    dr:command-top-of-output "/evpn-information";
    dr:command-full-name "request drend juniper-netconf-get";
    dr:command-help "Default <get> rpc";

    output {
      container network-instances { 
        list network-instance {
          key "name";
          dr:source "/rt-instances/rt-instance";
          dr:fieldnum 151;

          leaf name {
            type string;
            dr:source "instance_name";
            dr:fieldnum 51;
          }
          container protocols {
            dr:fieldnum 151;
            container protocol {
              dr:source "protocols/protocol";
              dr:fieldnum 151;
              container evpn {
                dr:source "evpn";
                dr:fieldnum 151;
                uses rend-evpn-instance-statistics;

                list interfaces {
                  description "Interfaces";
                  key "name";
                  dr:source "interfaces";
                  dr:fieldnum 152;
                  uses rend-interface-group;
                }

                list irb-interfaces {
                  description "IRB interfaces";
                  key "name";
                  dr:source "irb-interfaces";
                  dr:fieldnum 153;
                  uses rend-irb-interface-group;
                }

                list peer {
                  description "Remote evpn peers";
                  key "peer-address";
                  dr:source "peer";
                  dr:fieldnum 154;
                  uses rend-peer-group;
                }
                list sg-db {
                  description "Multicast source groups";
                  key "ethernet-tag-id group source";
                  dr:source "sg-db";
                  dr:fieldnum 156;
                  uses rend-sgdb-group;
                }

                list ethernet-segment {
                  description "Ethernet segment identifiers";
                  key "esi";
                  dr:source "ethernet-segment";
                  dr:fieldnum 155;
                  uses rend-ethernet-segment-group;
                }

                container assisted-replication {
                  dr:source "assisted-replication";
                  dr:fieldnum 157;
                  uses rend-assisted-replication;
                }

              }
            }
          }
        }
      }
    }
  }

  notification evpn-designated-forwarder-change {
    dr:source-notification-name "change-designated-forwarder";
    container network-instances {
      dr:source "/notification/change-designated-forwarder/rt-instances";
      dr:fieldnum 151;
      list network-instance {
        dr:source "rt-instance";
        dr:fieldnum 151;
        key name;
        leaf name {
          type string;
          dr:source instance-name;
          dr:fieldnum 51;
        }
        container protocols {
          dr:fieldnum 151;
          dr:source "protocols";
          container protocol {
            dr:source "protocol";
            dr:fieldnum 151;
            container evpn {
              dr:source "evpn";
              dr:fieldnum 151;
              list ethernet-segment {
                dr:source ethernet-segment;
                dr:fieldnum 155;
                key esi;
                leaf esi {
                  type string;
                  dr:source "esi";
                  dr:fieldnum 71;
                }
                leaf designated-forwarder {
                  type string;
                  dr:source "designated-forwarder";
                  dr:fieldnum 76;
                }
              }
            }
          }
        }
      }
    }
  }
}
