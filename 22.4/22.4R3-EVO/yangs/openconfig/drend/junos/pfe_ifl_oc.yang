/*
 * $Id$
 *
 * Copyright (c) 2006-2016, Juniper Networks, Inc.
 * All rights reserved.
 *
 */

module pfe_ifl_oc {

  yang-version "1";

  // namespace
  namespace "http://juniper.net/yang/pfe-ifl-oc";

  prefix "pfe-ifl-oc";

  //import ietf-yang-types { prefix yang; }
  import openconfig-interfaces { prefix ocif; }
  import drend { prefix dr; }
  import jnpr-proto { prefix jnpr-proto; }


  // meta
  organization "Juniper Network Inc.";

  contact "www.juniper.net";

  grouping pfe-ifl {
    uses ocif:interfaces-top {
      augment "interfaces" {
	dr:backup-supported;
        dr:source "/junos/system/linecard/interface/logical/usage/";
        dr:fieldnum 151;
      }
      augment "interfaces/interface" {
        dr:source "/junos/system/linecard/interface/logical/usage/";
        dr:fieldnum 151;
      }
      augment "interfaces/interface/subinterfaces" {
        dr:source "/junos/system/linecard/interface/logical/usage/";
        dr:fieldnum 151;
      }
      augment "interfaces/interface/subinterfaces/subinterface" {
        dr:source "/junos/system/linecard/interface/logical/usage/";
        dr:fieldnum 51;
      }
      augment "interfaces/interface/subinterfaces/subinterface/state" {
        dr:source "/junos/system/linecard/interface/logical/usage/";
        dr:fieldnum 151;
      }
      augment "interfaces/interface/subinterfaces/subinterface/state/counters" {
        dr:source "/junos/system/linecard/interface/logical/usage/";
        dr:fieldnum 151;
      }
      augment "interfaces/interface/subinterfaces/subinterface/state/counters/in-octets" {
        dr:source "/junos/system/linecard/interface/logical/usage/";
        dr:fieldnum 51;
      }
      augment "interfaces/interface/subinterfaces/subinterface/state/counters/in-unicast-pkts" {
        dr:source "/junos/system/linecard/interface/logical/usage/";
        dr:fieldnum 52;
      }
      augment "interfaces/interface/subinterfaces/subinterface/state/counters/in-multicast-pkts" {
        dr:source "/junos/system/linecard/interface/logical/usage/";
        dr:fieldnum 54;
      }
      augment "interfaces/interface/subinterfaces/subinterface/state/counters/out-octets" {
        dr:source "/junos/system/linecard/interface/logical/usage/";
        dr:fieldnum 58;
      }
      augment "interfaces/interface/subinterfaces/subinterface/state/counters/out-unicast-pkts" {
        dr:source "/junos/system/linecard/interface/logical/usage/";
        dr:fieldnum 59;
      }
      augment "interfaces/interface/subinterfaces/subinterface/state/counters/out-multicast-pkts" {
        dr:source "/junos/system/linecard/interface/logical/usage/";
        dr:fieldnum 61;
      }
    }
  }

  dr:command-app "agentd";
  dr:sub-component "pfe-ifl";
  jnpr-proto:message-id "PFE-IFL-OC-MESSAGE-ID";

  rpc juniper-netconf-get {
    output {
        uses pfe-ifl;
    }
  }
}
