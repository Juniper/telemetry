/*
* $Id$
*
* Copyright (c) 2006-2019, Juniper Networks, Inc.
* All rights reserved.
*
*/

module pfe_mpls_ldp_p2mp_lsp_branch_oc {

  yang-version "1";

  // namespace
  namespace "http://juniper.net/yang/pfe-mpls-ldp-p2mp-lsp-branch-oc";

  prefix "mpls-ldp-oc";

  //import ietf-yang-types { prefix yang; }
  import openconfig-mpls { prefix oc-mpls; }
  import jnx-aug-openconfig-mpls { prefix jnx-aug-oc-mpls; }
  import drend { prefix dr; }
  import jnpr-proto { prefix jnpr-proto; }

  // meta
  organization "Juniper Network Inc.";

  contact "www.juniper.net";

  grouping mpls-ldp {
    uses oc-mpls:mpls-top {
      augment "mpls" {
        dr:source "/junos/services/ldp/p2mp/label-switched-path/branch/usage/";
        dr:fieldnum 151;
      }
      augment "mpls/signaling-protocols" {
        dr:source "/junos/services/ldp/p2mp/label-switched-path/branch/usage/";
        dr:fieldnum 151;
      }
      augment "mpls/signaling-protocols/ldp" {
        dr:source "/junos/services/ldp/p2mp/label-switched-path/branch/usage/";
        dr:fieldnum 151;
      }
      augment "mpls/signaling-protocols/ldp" {
        uses jnx-aug-oc-mpls:jnx-ldp-p2mp-lsp-branches-container {
          augment "p2mp-lsp-branches" {
            dr:source "/junos/services/ldp/p2mp/label-switched-path/branch/usage/";
            dr:fieldnum 151;
          }
          augment "p2mp-lsp-branches/p2mp-lsp-branch" {
            dr:source "/junos/services/ldp/p2mp/label-switched-path/branch/usage/";
            dr:fieldnum 151;
          }
          augment "p2mp-lsp-branches/p2mp-lsp-branch/state" {
            dr:source "/junos/services/ldp/p2mp/label-switched-path/branch/usage/";
            dr:fieldnum 151;
          }
          augment "p2mp-lsp-branches/p2mp-lsp-branch/state/counters" {
            dr:source "/junos/services/ldp/p2mp/label-switched-path/branch/usage/";
            dr:fieldnum 151;
          }
        }
      }
    }
  }

  dr:command-app "agentd";
  dr:sub-component "pfe-mpls-ldp-p2mp-lsp-branch";
  jnpr-proto:message-id "PFE-MPLS-LDP-P2MP-LSP-BRANCH-OC-MESSAGE-ID";

   rpc juniper-netconf-get {
       output {
         uses mpls-ldp;
       }
   }
}
