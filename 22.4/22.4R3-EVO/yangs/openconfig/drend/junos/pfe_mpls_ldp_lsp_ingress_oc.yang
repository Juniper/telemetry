/*
 * $Id$
 *
 * Copyright (c) 2006-2019, Juniper Networks, Inc.
 * All rights reserved.
 *
 */

module pfe_mpls_ldp_lsp_ingress_oc {

  yang-version "1";

  // namespace
  namespace "http://juniper.net/yang/ldp";

  prefix "mpls-ldp-oc";

  //import ietf-yang-types { prefix yang; }
  import openconfig-mpls { prefix oc-mpls; }
  import jnx-aug-openconfig-mpls { prefix jnx-aug-oc-mpls; }
  import drend { prefix dr; }
  import jnpr-proto { prefix jnpr-proto; }

  // meta
  organization "Juniper Network Inc.";

  contact "www.juniper.net";

  grouping mpls-ldp {
    uses oc-mpls:mpls-top {
      augment "mpls" {
        dr:source "/junos/services/ldp/label-switched-path/ingress/usage/";
        dr:fieldnum 151;
      }
      augment "mpls/signaling-protocols" {
        dr:source "/junos/services/ldp/label-switched-path/ingress/usage/";
        dr:fieldnum 151;
      }
      augment "mpls/signaling-protocols/ldp" {
        dr:source "/junos/services/ldp/label-switched-path/ingress/usage/";
        dr:fieldnum 151;
      }
      augment "mpls/signaling-protocols/ldp" {
        uses jnx-aug-oc-mpls:jnx-ldp-lsps-ingress-container {
          augment "lsp-ingress-policies" {
            dr:source "/junos/services/ldp/label-switched-path/ingress/usage/";
            dr:fieldnum 151;
          }
          augment "lsp-ingress-policies/lsp-ingress-policy" {
            dr:source "/junos/services/ldp/label-switched-path/ingress/usage/";
            dr:fieldnum 151;
          }
          augment "lsp-ingress-policies/lsp-ingress-policy/state" {
            dr:source "/junos/services/ldp/label-switched-path/ingress/usage/";
            dr:fieldnum 151;
          }
          augment "lsp-ingress-policies/lsp-ingress-policy/state/counters" {
            dr:source "/junos/services/ldp/label-switched-path/ingress/usage/";
            dr:fieldnum 151;
          }
        }
      }
    }
  }
  dr:command-app "agentd";
  dr:sub-component "pfe-mpls-ldp-lsp-ingress";
  jnpr-proto:message-id "LDP-LSP-INGRESS-STATS-MESSAGE-ID";

  rpc juniper-netconf-get {
    output {
        uses mpls-ldp;
    }
  }
}
