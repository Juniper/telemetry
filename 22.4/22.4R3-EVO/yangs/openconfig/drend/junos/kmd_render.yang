/*
 * $Id$
 *
 * Copyright (c) 2017, Juniper Networks, Inc.
 * All rights reserved.
 *
 */

module kmd_render {

    yang-version "1";

    // namespace
    namespace "http://juniper.net/yang/kmd";

    prefix "kmd_render";

    import drend { prefix dr; }
    import jnpr-proto { prefix jnpr-proto; }


    // meta
    organization "Juniper Network Inc.";

    contact "www.juniper.net";

    grouping kmd-port {
        leaf remote-ip {
            type string;
            dr:source "remote_ip";  // key
            dr:fieldnum 51;
        }
        leaf local-ip {
            type string;
            dr:source "local_ip";  // key
            dr:fieldnum 52;
        }
        leaf number-ipsec-sa-created {
            type uint32;
            dr:source "num_ipsec_sa_created";
            dr:fieldnum 53;
        }
        leaf number-ipsec-sa-deleted {
            type uint32;
            dr:source "num_ipsec_sa_deleted";
            dr:fieldnum 54;
        }
        leaf number-ipsec-sa-rekey {
            type uint32;
            dr:source "num_ipsec_sa_rekey";
            dr:fieldnum 55;
        }
        leaf exchange-type {
            type string;
            dr:source "exchange_type";
            dr:fieldnum 56;
        }
        leaf in-bytes {
            type uint32;
            dr:source "in_bytes";
            dr:fieldnum 57;
        }
        leaf in-packets {
            type uint32;
            dr:source "in_pkts";
            dr:fieldnum 58;
        }
        leaf out-bytes {
            type uint32;
            dr:source "out_bytes";
            dr:fieldnum 59;
        }
        leaf out-packets {
            type uint32;
            dr:source "out_pkts";
            dr:fieldnum 60;
        }
        leaf delete-payload-received {
            type uint32;
            dr:source "delete_payload_recv";
            dr:fieldnum 61;
        }
        leaf delete-payload-transmitted {
            type uint32;
            dr:source "delete_payload_sent";
            dr:fieldnum 62;
        }
        leaf dpd-request-payload-received {
            type uint32;
            dr:source "dpd_req_payload_recv";
            dr:fieldnum 63;
        }
        leaf dpd-request-payload-transmitted {
            type uint32;
            dr:source "dpd_req_payload_sent";
            dr:fieldnum 64;
        }
        leaf dpd-response-payload-received {
            type uint32;
            dr:source "dpd_res_payload_recv";
            dr:fieldnum 65;
        }
        leaf dpd-response-payload-transmitted {
            type uint32;
            dr:source "dpd_res_payload_sent";
            dr:fieldnum 66;
        }
        leaf dpd-response-payload-missed {
            type uint32;
            dr:source "dpd_res_payload_missed";
            dr:fieldnum 67;
        }
        leaf dpd-response-payload-maximum-delay {
            type uint32;
            dr:source "dpd_res_payload_max_delay";
            dr:fieldnum 68;
        }
        leaf dpd-response-seq-payload-missed {
            type uint32;
            dr:source "dpd_res_seq_payload_missed";
            dr:fieldnum 69;
        }
        leaf invalid-spi-notify-received {
            type uint32;
            dr:source "invalid_spi_notify_recv";
            dr:fieldnum 70;
        }
        leaf invalid-spi-notify-transmitted {
            type uint32;
            dr:source "invalid_spi_notify_sent";
            dr:fieldnum 71;
        }
        leaf routing-instance {
            type string;
            dr:source "vrf_name";  // key
            dr:fieldnum 72;
        }
    }

    // Daemon which handles this hierarchy
    dr:command-app "kmd";
    dr:sub-component "key-management";
    jnpr-proto:message-id "KMD-RENDER-MESSAGE-ID";

    // rpc for fetching IKE stats for a particular IKE SA since there can be simultaneous IKE negotiations.
    rpc juniper-netconf-get {
        //dr:command-top-of-output "/oc-kmd-information";
        //dr:command-help "Default <get> rpc";
        output {
            container junos {
                config false;
                container ike-security-associations {
                    dr:source "/IkeSensors/ike_security_associations";
                    dr:fieldnum 151;
                    list ike-security-association {
                        dr:source "ike_security_association";
                        dr:fieldnum 151;
                        key "remote-ip local-ip routing-instance";
                        uses kmd-port;
                    }
                }
            }
        }
    }
}
