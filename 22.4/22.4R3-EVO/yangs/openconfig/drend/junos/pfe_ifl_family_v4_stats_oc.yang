/*
 * $Id$
 *
 * Copyright (c) 2006-2021, Juniper Networks, Inc.
 * All rights reserved.
 *
 */

module pfe_ifl_family_v4_stats_oc {

  yang-version "1";

  // namespace
  namespace "http://juniper.net/yang/pfe-ifl-family-v4-stats-oc";

  prefix "pfe-ifl-family-v4-stats-oc";

  //import ietf-yang-types { prefix yang; }
  //import openconfig-interfaces { prefix oc-if; }
  import openconfig-if-ip { prefix ocip; }
  import drend { prefix dr; }
  import jnpr-proto { prefix jnpr-proto; }


  // meta
  organization "Juniper Network Inc.";

  contact "www.juniper.net";

  grouping pfe-ifl-family-v4 {
    uses ocip:ipv4-top {
      augment "ipv4" {
        dr:source "/junos/system/linecard/interface/logical/family/ipv4/usage/";
        dr:fieldnum 151;
      }
      augment "ipv4/state" {
        dr:source "/junos/system/linecard/interface/logical/family/ipv4/usage/";
        dr:fieldnum 151;
      }
      augment "ipv4/state/counters" {
        dr:source "/junos/system/linecard/interface/logical/family/ipv4/usage/";
        dr:fieldnum 151;
      }
      augment "ipv4/state/counters/in-pkts" {
        dr:source "/junos/system/linecard/interface/logical/family/ipv4/usage/";
        dr:fieldnum 51;
      }
      augment "ipv4/state/counters/in-octets" {
        dr:source "/junos/system/linecard/interface/logical/family/ipv4/usage/";
        dr:fieldnum 52;
      }
      augment "ipv4/state/counters/in-multicast-pkts" {
        dr:source "/junos/system/linecard/interface/logical/family/ipv4/usage/";
        dr:fieldnum 53;
      }
      augment "ipv4/state/counters/in-multicast-octets" {
        dr:source "/junos/system/linecard/interface/logical/family/ipv4/usage/";
        dr:fieldnum 54;
      }
      augment "ipv4/state/counters/out-pkts" {
        dr:source "/junos/system/linecard/interface/logical/family/ipv4/usage/";
        dr:fieldnum 55;
      }
      augment "ipv4/state/counters/out-octets" {
        dr:source "/junos/system/linecard/interface/logical/family/ipv4/usage/";
        dr:fieldnum 56;
      }
      augment "ipv4/state/counters/out-multicast-pkts" {
        dr:source "/junos/system/linecard/interface/logical/family/ipv4/usage/";
        dr:fieldnum 57;
      }
      augment "ipv4/state/counters/out-multicast-octets" {
        dr:source "/junos/system/linecard/interface/logical/family/ipv4/usage/";
        dr:fieldnum 58;
      }
    }
  }

  dr:command-app "agentd";
  dr:sub-component "pfe-ifl-family-v4";
  jnpr-proto:message-id "PFE-IFL-FAMILY-V4-STATS-OC-MESSAGE-ID";

  rpc juniper-netconf-get {
    output {
      container interfaces {
        dr:source "/junos/system/linecard/interface/logical/usage/";
        dr:fieldnum 151;
        list interface {
          dr:source "/junos/system/linecard/interface/logical/usage/";
          dr:fieldnum 151;
          key "name" ;
          leaf name {
            type string;
            dr:fieldnum 51;
          }
          container subinterfaces {
            dr:source "/junos/system/linecard/interface/logical/usage/";
            dr:fieldnum 151;
            list subinterface {
              dr:source "/junos/system/linecard/interface/logical/usage/";
              dr:fieldnum 151;
              key "index" ;
              leaf index {
                type uint32;
                dr:fieldnum 51;
              }
              uses pfe-ifl-family-v4;
            }
          }
        }
      }
    }
  }
}
