module jnx-aug-openconfig-platform {
    yang-version "1";

    namespace "http://yang.juniper.net/openconfig/augment/platform";

    prefix "jnx-oc-platform";

    import openconfig-platform { prefix oc-platform; }
    import openconfig-platform-cpu { prefix oc-cpu; }
    import openconfig-platform-linecard { prefix oc-linecard; }
    import openconfig-platform-types { prefix oc-platform-types; }
    import openconfig-yang-types { prefix oc-yang; }
    import junos-extension { prefix junos; }

    organization "Juniper Networks";

    description
       "This module contains JUNOS augments to OpenConfig components model";

    revision "2021-08-30" {
        description "Augmenting new leaves for
        /components/component/fabric/state and
        /components/component/backplane/state and
        /components/component/fpc/state and
        /components/component/power-supply/state and
        /components/component/fan/state and
        /components/component/storage/state
        containers";
    }

    revision "2021-09-15" {
        description "Augmenting new container control-card
        for /components/component/ path and defining generic
        properties/property list for /components/component/
        /<component-name>/properties/property path";
    }

    revision "2021-08-03" {
        description "Augmenting new leaves for
        /components/component/chassis/state and
        /components/component/linecard/state
        containers";
    }

    revision "2021-12-27" {
        description "Augmenting new leaves for
        /components/component/bios/state/software-version and
        /components/component/bootloader/state/software-version and
        leafs";
    }

    revision "2019-11-05" {
        description "Initial revision";
    }

    augment "/oc-platform:components/oc-platform:component/oc-platform:cpu/" +
        "oc-cpu:utilization/oc-cpu:state" {
        leaf name {
            type string;
            description "Indicates the name related to the utilization of
            the CPU";
        }
    }

    grouping chassis-info {
        description
        "Top level operational information for chassis component";
        leaf base-mac-address {
             type string;
             description
             "Public mac-address exposed to outside world";
        }
        leaf base-num-mac-addresses {
             type uint32;
             description
             "Total numbers of mac addresses (public and private) supported";
        }
    }

    grouping linecard-info {
        description
        "Top level operational state information for Linecard component";
        leaf "boot-time" {
            type string;
            description
            "Uptime for the linecard";
        }
        leaf "recent-reset-cause" {
            type string;
            description
            "Offline reason string for the linecard";
        }
    }

    grouping hwd-component-property-info {
        container properties {
            description
            "Operational state for component properties";
            list property {
                key "name";
                description
                "Top level information for component properties";
                leaf "name" {
                    type string;
                    description
                    "System-supplied name of the property";
                }
                container "state" {
                    description
                    "Operational state data for each property";
                    leaf value {
                        type string;
                        description
                        "Property values can take on a variety of types.";
                    }
                    leaf configurable {
                        type boolean;
                        description
                        "Indication whether the property is user-configurable";
                    }
                }
            }
        }
    }

    grouping control-card-info {
        container control-card {
            description
            "Container for component control-card";
            uses hwd-component-property-info;
        }
    }

    grouping component-state {
        leaf base-mac-address {
            type oc-yang:mac-address;
            description
            "Public mac-address exposed to outside world";
        }
        leaf base-num-mac-addresses {
            type uint32;
            description
            "Total numbers of mac addresses (public and private) supported";
        }
        leaf boot-time {
            type string;
            description
            "Uptime for the linecard";
        }
        leaf recent-reset-cause {
            type string;
            description
            "Offline reason string for the linecard";
        }
    }

    augment "/oc-platform:components/oc-platform:component" {
        description
        "Hardware or software component in the system";
        uses control-card-info;
    }

    augment "/oc-platform:components/oc-platform:component/" +
        "oc-platform:state" {
        description
        "Operational state data for generic components";
        uses component-state;
    }

    augment "/oc-platform:components/oc-platform:component/" +
        "oc-platform:chassis" {
        description
        "Data for chassis components";
        uses hwd-component-property-info;
    }

    augment "/oc-platform:components/oc-platform:component/" +
        "oc-platform:chassis/oc-platform:state" {
        description
        "Operational state data for chassis components";
        uses chassis-info;
    }

    grouping storage-info {
        description
        "Top level operational state information for Storage component";
        leaf "model" {
            type string;
            description
            "Storage component model number";
        }
        leaf "description" {
            type string;
            description
            "Storage component description";
        }
        leaf "size" {
            type uint32;
            description
            "Storage component size";
        }
    }

    grouping hwd-component-state-info {
      leaf type {
        type union {
          type identityref {
            base oc-platform-types:OPENCONFIG_HARDWARE_COMPONENT;
          }
          type identityref {
            base oc-platform-types:OPENCONFIG_SOFTWARE_COMPONENT;
          }
        }
        description
        "Type of component as identified by the system";
      }
      leaf id {
        type string;
        description
          "Unique identifier assigned by the system for the
          component";
      }
      leaf location {
        type string;
        description
          "System-supplied description of the location of the
          component within the system. This could be a bay position,
          slot number, socket location, etc. For component types that
          have an explicit slot-id attribute, such as linecards, the
         system should populate the more specific slot-id.";
      }
      leaf description {
        type string;
        description
          "System-supplied description of the component";
      }
      leaf mfg-name {
        type string;
        description
          "System-supplied identifier for the manufacturer of the
          component.  This data is particularly useful when a
          component manufacturer is different than the overall
          device vendor.";
      }
      leaf mfg-date {
        type oc-yang:date;
        description
          "System-supplied representation of the component's
          manufacturing date.";
      }
      leaf hardware-version {
        type string;
        description
          "For hardware components, this is the hardware revision of
          the component.";
      }
      leaf firmware-version {
        type string;
        description
          "For hardware components, this is the version of associated
          firmware that is running on the component, if applicable.";
      }
      leaf software-version {
        type string;
        description
          "For software components such as operating system or other
          software module, this is the version of the currently
          running software.";
      }
      leaf serial-no {
        type string;
        description
          "System-assigned serial number of the component.";
      }
      leaf part-no {
        type string;
        description
          "System-assigned part number for the component.  This should
          be present in particular if the component is also an FRU
         (field replaceable unit)";
      }
      leaf removable {
        type boolean;
        description
          "If true, this component is removable or is a field
          replaceable unit";
      }
      leaf oper-status {
        type identityref {
          base oc-platform-types:COMPONENT_OPER_STATUS;
        }
        description
         "If applicable, this reports the current operational status
         of the component.";
      }
      leaf empty {
        type boolean;
        default false;
        description
          "The empty leaf may be used by the device to indicate that a
          component position exists but is not populated.  Using this
          flag, it is possible for the management system to learn how
          many positions are available (e.g., occupied vs. empty
          linecard slots in a chassis).";
      }
      leaf "parent" {
        type string;
        description
          "Reference to the name of the parent component.  Note that
          this reference must be kept synchronized with the
          corresponding subcomponent reference from the parent
          component.";
      }
    }

    augment "/oc-platform:components/oc-platform:component/oc-platform:backplane/oc-platform:state" {
        uses hwd-component-state-info;
    }

    augment "/oc-platform:components/oc-platform:component/oc-platform:fabric/oc-platform:state" {
        uses hwd-component-state-info;
    }

    augment "/oc-platform:components/oc-platform:component/oc-platform:power-supply/oc-platform:state" {
        uses hwd-component-state-info;
    }

    augment "/oc-platform:components/oc-platform:component/oc-platform:fan/oc-platform:state" {
        uses hwd-component-state-info;
    }

    augment "/oc-platform:components/oc-platform:component/oc-platform:storage/oc-platform:state" {
        uses storage-info;
    }

    augment "/oc-platform:components/oc-platform:component/" +
        "oc-linecard:linecard/oc-linecard:state" {
        description
        "Operational state data for Linecard component";
        uses hwd-component-state-info;
        uses linecard-info;
    }

    augment "/oc-platform:components/oc-platform:component/" +
        "oc-platform:integrated-circuit/oc-platform:state" {
        description "Data for chip component, such as ASIC or NPU";

        container properties {
            description "Contianer for chip component";
            list property {

                key name;
                description "Name of the chip component";

                leaf name {
                    description "Name for chip component";
                    type string;
                }

                container state {
                    description "Container for chip component state";

                    leaf value {
                        description "Data value for chip component";
                        type uint64;
                    }
                }
            }
        }
    }
    augment "/oc-platform:components" {
      junos:translation-script "openconfig-platform.slax";
    }

}
