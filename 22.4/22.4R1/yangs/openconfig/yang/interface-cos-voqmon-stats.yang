module interface-cos-voqmon-stats {

  yang-version "1";

  // namespace
  namespace "http://juniper.net/yang/interface-cos-voqmon-stats";

  prefix "interface-cos-voqmon-stats";

  // meta
  organization "Juniper Networks";

  description
    "This module provides data definitions for exporting VoqMon Stats
    ";

  grouping interface-voqmon-stat-detail {
    container cos {
      description
      "Describes voqmon stat details";
      container interfaces {
        description
        "Describes interface details";
        list interface {
          description
          "Describes interface voqmon stats information";
          key interface-id;

          leaf interface-id {
            type string;
            description
            "Describes interface name";
          }

          container input {
            description
            "Describes voqmon data related to ingress interface";
            container queues {
              description
              "Describes interface input queues info";
              list queue {
                description
                "Describes voqmon stats per each queue";
                key queue-num;

                leaf queue-num {
                  type uint8;
                  description
                  "Describes queue number";
                }

                container pfes {
                  description
                  "Describes ingress interface pfe voqmon stats";
                  list pfe {
                    description
                    "Describes interface voqmon stats per each pfe";
                    key pfe-index;

                    leaf pfe-index {
                      type uint8;
                      description
                      "Describes pfe index";
                    }

                    leaf peak-queue-length-bytes {
                      type uint64;
                      description
                      "Describes maximum observed queue length";
                    }

                    leaf peak-queue-length-percent {
                      type uint64;
                      description
                      "Describes maximum observed queue length percentage";
                    }

                    leaf cur-queue-length-bytes {
                      type uint64;
                      description
                      "Describes current observed queue length";
                    }

                    leaf cur-queue-length-percent {
                      type uint64;
                      description
                      "Describes current observed queue length percentage";
                    }

                    leaf avg-queue-length-bytes {
                      type uint64;
                      description
                      "Describes average observed queue length";
                    }

                    leaf avg-queue-length-percent {
                      type uint64;
                      description
                      "Describes average observed queue length percentage";
                    }
                  }
                }
              }
            }
          }
        }
      }
    }
  }

  grouping interface-cos-voqmon-stats {
    description
      "This describes the data exported by PFE jvision voqmon sensor";

    container junos {
      config false;
      description "JunOS OS";

      container system {
        description "Junos System";

        container linecard {
          description "Contains PFE resources";

          container qmon-sw {
            description "Voqmon sensor data";

            uses interface-voqmon-stat-detail;
          }
        }
      }
    }
  }

  uses interface-cos-voqmon-stats;

}
