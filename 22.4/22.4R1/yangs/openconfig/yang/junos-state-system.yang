module junos-state-system {
  yang-version 1.1;
  namespace "http://yang.juniper.net/junos/state/system";
  prefix js-sys;

  import junos-base-extensions {
    prefix junos-base;
  }

  import junos-state {
    prefix js;
  }

  organization
    "Juniper Networks, Inc.";

  contact
    "Juniper Networks, Inc.

     1133 Innovation Way
     Sunnyvale, CA

     +1 888 314-5822

     E-mail: yang-support@juniper.net";

  description
    "This module contains a collection of top level nodes for JUNOS
     system state data.

     Copyright (c) 2022 Juniper Networks, Inc.
     All rights reserved.";

  revision 2022-01-19 {
    description
      "Initial revision";
    reference "0.1.0";
  }

  junos-base:version "0.1.0";

  grouping system-global-top {
    description
      "Global attributes for system state";

    leaf host-name {
      type string;
      description
        "Hostname for this router";
    }
  }

  grouping system-top {
    description
      "Top-level grouping for JUNOS system state data";

    container system {
      description
        "Encapsulating container for all JUNOS system state";

      uses system-global-top;
    }
  }

  augment "/js:state" {
    description
      "Adds system domain to top-level state";

    uses system-top;
  }
}
